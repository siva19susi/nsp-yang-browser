module vprn {
    namespace "http://www.nokia.com/management-solutions/vprn";
    yang-version 1.1;
    prefix "vprn";
    import ietf-inet-types { prefix "inet-types"; }
    import qos-filter-common { prefix "qos-filter-common"; }
    import sap-common { prefix "sap-common"; }
    import svc-common { prefix "svc-common"; }
    import ip-transport-common { prefix "ip-transport-common"; }
    organization "NOKIA Corp";
    contact "";
    description "";

    revision "2024-08-20" {
        description
            "Change init-delay to allow 0";
    }
    revision "2023-08-18" {
        description
            "23.11 changes - adding support for NSPF-255545, NSPF-301616, ip-transport and BGP-EVPN";
    }
    revision "2023-05-02" {
        description
            "23.8 changes - adding eBGP group prefix";
    }
    revision "2022-09-09" {
        description
            "22.9 changes - Routed VPLS
                                   - Remove Mandatory for ipv4 address
                                   - update type for primary/secondary ipv4 address";
    }
    revision "2022-05-13" {
            description
                    "22.6 changes - Auto-RD";
    }
    revision "2021-09-03" {
        description
                "21.11 changes";
    }
    revision "2021-06-08" {
        description
                "Initial revision.";
    }

    typedef admin-state {
        type enumeration {
            enum unlocked;
            enum locked;
        }
        description
            "admin-state specifies the general administrative state for the
             typical SR OS entity that supports administrative states.";
    }

    typedef peer-type {
        type enumeration {
            enum "no-type"                      { value 1; }
            enum "internal"                     { value 2; }
            enum "external"                     { value 3; }
        }
        description "Specifies a neighbor as type internal or external.";
    }

    typedef ip-address {
        type inet-types:ip-address-no-zone;
        description "An IP address.";
    }

    typedef ipv4-address {
        type inet-types:ipv4-address-no-zone {
            pattern "[0-9\\.]*";
            pattern "(([0-9]|[1-9][0-9]|1[0-9][0-9]|2[0-4][0-9]|25[0-5])\\.){3}([0-9]|[1-9][0-9]|1[0-9][0-9]|2[0-4][0-9]|25[0-5])(%[\\p{N}\\p{L}]+)?";
        }
        description "An IPv4 address.";
    }

    typedef rt-type {
        type enumeration {
            enum imp;
            enum exp;
            enum import-export;
        }
    }

    typedef vpn-route-distinguisher-or-auto-rd {
        type union {
            type enumeration {
                enum "auto-rd"                      { value 1; }
            }
            type string;
        }
        description
            "The vpn-route-distinguisher-or-auto-rd defines either a
             vpn-route-distinguisher or an enumeration indicating use of
             automatically assigned route-distinguisher.";
    }

    typedef ieee-address {
        type string {
            pattern "([0-9a-fA-F]{2}(:[0-9a-fA-F]{2}){5})|([0-9a-fA-F]{2}(-[0-9a-fA-F]{2}){5})";
        }
        description "The ieee-address type represents an IEEE 802 MAC address.";
    }

    grouping bgp-family {
        container family {
            presence "Enable the family context";
            description "Enable the family context";

            leaf ipv4 {
                type boolean;
                description "Add support for the IPv4 address family";
            }

            leaf ipv6 {
                type boolean;
                description "Advertise MP-BGP support for the IPv6 address family";
            }

            leaf mcast-ipv4 {
                type boolean;
                description "Advertise support for the MCAST-IPv4 address family";
            }

            leaf flow-ipv4 {
                type boolean;
                description "Advertise support for the flowspec-IPv4 address family";
            }

            leaf flow-ipv6 {
                type boolean;
                description "Advertise support for the flowspec-IPv6 address family";
            }

            leaf mcast-ipv6 {
                type boolean;
                description "Advertise support for the MCAST-IPv6 address family";
            }

            leaf label-ipv4 {
                type boolean;
                description "Advertise support for the label-IPv4 address family";
            }

        } // container family
    }


    grouping configuration-details {
        container vprn {
            uses svc-common:svc-details;

            container site-details{
                list site {
                    key "device-id site-name";

                    uses svc-common:site-details;

                    leaf ne-service-id {
                        type uint32 {
                            range "1..2147483647";
                        }
                        description "Specify Service Id";
                    }

                    leaf autonomous-system {
                        type uint32 {
                            range "1..max";
                        }
                        description "AS number advertised to peers for this router";
                    }

                    leaf ecmp {
                        type int32 {
                            range "1..64";
                        }
                        description "Maximum ECMP routes information";
                    }

                    leaf router-id {
                        type ip-address;
                        description "Unique router ID for the router in the AS";
                    }

                    leaf export-inactive-bgp {
                        type boolean;
                        description "Export best BGP route as a VPN-IP route even if inactive due to a preferred route from another PE";
                    }

                    leaf route-distinguisher {
                        type vpn-route-distinguisher-or-auto-rd;
                        description "Route distinguisher";
                    }

                    leaf route-distinguisher-type {
                        type enumeration {
                            enum "type0"                         { value 0; }
                            enum "type1"                       { value 1; }
                            enum "type2"                          { value 2; }
                        }
                        description "Route distinguisher type - Mandatory for NFMP managed nodes";
                    }

                    leaf-list vrf-import  {
                        type string;
                        description "Name of the import policy. The name of the policy is limited to 64 characters except for the first policy.";
                    }

                    leaf-list vrf-export  {
                        type string;
                        description "Name of the export policy. The name of the policy is limited to 64 characters except for the first policy.";
                    }

                    leaf bgp-ipvpn-admin-state {
                        type enumeration {
                            enum locked;
                            enum unlocked;
                        }
                        description "BGP-IPVPN Administrative State. Only applicable on SROS 21.X";
                        default unlocked;
                    }

                    list route-target {
                        key "target-type target-value";
                        description "Enter the vrf-target context";

                        leaf target-type {
                            type rt-type;
                            mandatory true;
                            description "The type of route target";
                        }

                        leaf target-value {
                            type string;
                            mandatory true;
                            description "The route target value";
                        }
                    } // list route-target

                    container auto-bind-tunnel {
                        description "Enter the auto-bind-tunnel context";
                        uses svc-common:auto-bind-tunnel-details;

                    } // container auto-bind-tunnel

                    container bgp-evpn {

                        leaf enable-evpn-mpls {
                            type boolean;
                            default "false";
                            description "Enable EVPN MPLS container";
                        }

                        container mpls {
                            when "../enable-evpn-mpls= 'true'";
                            leaf admin-state {
                                type admin-state;
                                default "locked";
                                description "Administrative state of BGP-EVPN MPLS";
                            }
                            leaf route-distinguisher {
                                type vpn-route-distinguisher-or-auto-rd;
                                description "Route distinguisher";
                            }
                            leaf-list vrf-import-policy  {
                                type string;
                                description "Name of the import policy. The name of the policy is limited to 64 characters except for the first policy.";
                            }

                            leaf-list vrf-export-policy  {
                                type string;
                                description "Name of the export policy. The name of the policy is limited to 64 characters except for the first policy.";
                            }

                            list route-target {
                                key "target-type target-value";
                                description "Enter the vrf-target context";

                                leaf target-type {
                                    type rt-type;
                                    mandatory true;
                                    description "The type of route target";
                                }

                                leaf target-value {
                                    type string;
                                    mandatory true;
                                    description "The route target value";
                                }
                            }

                            container auto-bind-tunnel {
                                description "Enter the auto-bind-tunnel context";
                                uses svc-common:auto-bind-tunnel-details;
                            }
                        }
                    }

                    leaf enable-max-routes {
                        type boolean;
                        default "false";
                        description "Enable maximum-routes container";
                    }

                    container maximum-routes {
                        when "../enable-max-routes= 'true'";
                        container maximum-ipv4-routes {
                            description "Enter the maximum-ipv4-routes context";
                            leaf maxNumberOfRoutes {
                                type int32 {
                                    range "1..2147483647";
                                    }
                                description "Maximum number of routes that are configured on this virtual router";
                            }
                            leaf maxNumberOfRoutesLogOnly {
                                type boolean;
                                default "false";
                                description "Action when the maximum number of routes, held within a VRF context, is reached";
                            }
                            leaf midRouteThreshold {
                                type uint32 {
                                    range "1..100";
                                }
                                units "percent";
                                description "Mid-level water marker for the number of routes which this VRF holds";
                            }

                        } // container maximum-ipv4-routes

                        container maximum-ipv6-routes {
                            description "Enter the maximum-ipv4-routes context";
                            leaf maxNumberOfRoutes {
                                type int32 {
                                    range "1..2147483647";
                                }
                                description "Maximum number of routes that are configured on this virtual router";
                            }
                            leaf maxNumberOfRoutesLogOnly {
                                type boolean;
                                default "false";
                                description "Action when the maximum number of routes, held within a VRF context, is reached";
                            }
                            leaf midRouteThreshold {
                                type uint32 {
                                    range "1..100";
                                }
                                units "percent";
                                description "Mid-level water marker for the number of routes which this VRF holds";
                            }

                        } // container maximum-ipv6-routes

                        container mc-maximum-routes {
                            description "Enter the mc-maximum-routes context";
                            leaf maxNumberOfMcastRoutes {
                                type int32 {
                                    range "1..2147483647";
                                }
                                description "Maximum number of multicast routes to be configured on this virtual router";
                            }
                            leaf maxNumberOfMcastRoutesLogOnly {
                                type boolean;
                                    default "false";
                                    description "Action when the maximum number of multicast routes, held within a VRF context, is reached";
                            }
                            leaf midRouteMcastThreshold {
                                type uint32 {
                                    range "1..100";
                                }
                                units "percent";
                                description "Mid-level water marker for the number of multicast routes which this VRF holds";
                            }

                        } // container mc-maximum-routes
                    }

                    container route-aggregation {
                        list aggregate {
                            key "ip-prefix";
                            description "Enter the aggregate list instance";

                            leaf ip-prefix {
                                type inet-types:ip-prefix;
                                description "Destination IP address prefix of the aggregate route";
                            }

                            leaf-list community {
                                type string;
                                max-elements 12;
                                ordered-by user;
                                description "Community name that is added to the aggregate route";
                            }

                            leaf summary-only {
                                type boolean;
                                default "false";
                                description "Advertise the aggregate route only";
                            }

                            leaf next-hop {
                                type enumeration {
                                    enum "blackhole"                    { value 1; }
                                    enum "indirect"               { value 3; }
                                }
                            }

                            leaf indirect {
                                type inet-types:ip-address-no-zone;
                                when "../next-hop = 'indirect'";
                                description "Address of the indirect next hop";
                            }
                        }
                    }

                    leaf-list snmp-community  {
                        type string;
                        description "SNMP v1/v2c community name associated with the VPRN";
                    }

                    leaf ignore-nh-metric {
                        type boolean;
                        description "Ignore next hop metric";
                    }

                    container bgp-vpn-backup {
                        description "Enter the bgp-vpn-backup context";

                        leaf ipv4 {
                            type boolean;
                            description "Allow BGP-VPN to be used as backup for IPv4 prefixes";
                        }

                        leaf ipv6 {
                            type boolean;
                            description "Allow BGP-VPN to be used as backup for IPv6 prefixes";
                        }

                    } // container bgp-vpn-backup


                    container interface-details{
                        list interface {
                            key "interface-name";
                            description "Enter the interface list instance";

                            leaf interface-name {
                                type string;
                                mandatory true;
                                description "Interface name.";
                            }

                            leaf description {
                                type string;
                                description "Text description";
                            }

                            leaf admin-state {
                                type admin-state;
                                default "unlocked";
                                description "Administrative state of the interface";
                            }

                            leaf loopback {
                                type boolean;
                                default "false";
                                description "Use interface as a loopback interface";
                            }

                            leaf ip-mtu {
                                type uint32 {
                                    range "512..9786";
                                }
                                units "bytes";
                                description "Interface IP MTU";
                            }

                            leaf ingress-stats {
                                type boolean;
                                default "false";
                                description "Collect ingress statistics";
                            }

                            leaf monitor-oper-group {
                                type string;
                                description "Operational group to monitor";
                            }

                            leaf mac {
                                type ieee-address;
                                description "MAC address for the interface";
                            }

                            leaf mac-accounting {
                                type boolean;
                                description "Enable MAC accounting functionality";
                            }

                            container isis {
                                when "../../../enable-isis = 'true'";

                                leaf isis-instance {
                                    type leafref {
                                        path "../../../../isis/isis-instance";
                                    }
                                    description "Instance ID for the IS-IS instance";
                                }

                                leaf admin-state {
                                    type admin-state;
                                    description "Administrative state of the IS-IS interface";
                                }

                                leaf passive {
                                    type boolean;
                                    description "Passive interface";
                                }

                                leaf level-capability {
                                    type enumeration {
                                        enum "1"                            { value 1; }
                                        enum "2"                            { value 2; }
                                        enum "1/2"                          { value 3; }
                                    }
                                    description "Routing level for instance";
                                }

                                leaf interface-type {
                                    type enumeration {
                                        enum "broadcast"                    { value 1; }
                                        enum "point-to-point"               { value 2; }
                                    }
                                    description "Interface type to broadcast or point-to-point";
                                }

                            }

                            container rip {
                                when "../../../enable-rip = 'true'";
                                leaf group-name {
                                    type leafref {
                                        path "../../../../rip/group/group-name";
                                    }
                                }
                            }

                            container ospf {
                                when "../../../enable-ospf = 'true'";
                                leaf area-id {
                                    type inet-types:ipv4-address;
                                    description "Area-ID attribute";
                                }

                                leaf interface-type {
                                    type enumeration {
                                        enum "broadcast"                    { value 1; }
                                        enum "point-to-point"               { value 3; }
                                    }
                                    description "Interface type to broadcast or point-to-point";
                                }

                                leaf passive {
                                    type boolean;
                                    description "Allow interface to be advertised as an OSPF interface without running the OSPF protocol";
                                }

                                leaf metric {
                                    type uint32 {
                                        range "1..65535";
                                    }
                                    description "Explicit route cost metric that is applied to the interface";
                                }

                                leaf authentication-key {
                                    type string;
                                    description "Authentication key";
                                }

                                leaf authentication-type {
                                    type enumeration {
                                        enum "password"                     { value 1; }
                                        enum "message-digest"               { value 2; }
                                    }
                                    description "Authentication type used on OSPF interface";
                                }

                                container bfd-liveness {
                                    presence "Enable the bfd-liveness context";
                                    description "Enable the bfd-liveness context";

                                    leaf remain-down-on-failure {
                                        type boolean;
                                        description "Force adjacency down on failure until session returns";
                                    }

                                } // container bfd-liveness

                                leaf admin-state {
                                    type admin-state;
                                    description "Administrative state of ospf interface";
                                }
                            }//container ospf

                            container hold-time {
                                description "Enter the hold-time context";

                                container ipv4 {
                                    description "Enter the ipv4 context";

                                    container up {
                                        description "Enter the up context";

                                        leaf seconds {
                                            type uint32 {
                                                range "1..1200";
                                            }
                                            units "seconds";
                                            description "Up hold time for the IP interface";
                                        }

                                    } // container up

                                    container down {
                                        description "Enter the down context";

                                        leaf seconds {
                                            type uint32 {
                                                range "1..1200";
                                            }
                                            units "seconds";
                                            description "Down hold time for the IP interface";
                                        }

                                        leaf init-only {
                                            type boolean;
                                            default "false";
                                            description "Apply delay only at interface configuration or reboot";
                                        }

                                    } // container down

                                } // container ipv4

                                container ipv6 {
                                    description "Enter the ipv6 context";

                                    container up {
                                        description "Enter the up context";

                                        leaf seconds {
                                            type uint32 {
                                                range "1..1200";
                                            }
                                            units "seconds";
                                            description "Up hold time for the IP interface";
                                        }

                                    } // container up

                                    container down {
                                        description "Enter the down context";

                                        leaf seconds {
                                            type uint32 {
                                                range "1..1200";
                                            }
                                            units "seconds";
                                            description "Down hold time for the IP interface";
                                        }

                                        leaf init-only {
                                            type boolean;
                                            default "false";
                                            description "Apply delay only at interface configuration or reboot";
                                        }

                                    } // container down

                                } // container ipv6

                            } // container hold-time

                            container cflowd-parameters {
                                description "Enter the cflowd-parameters context";

                                list sampling {
                                    key "sampling-type";
                                    description "Enter the sampling list instance";

                                    leaf sampling-type {
                                        type enumeration {
                                            enum unicast                        { value 1; }
                                            enum multicast                      { value 2; }
                                            enum both                           { value 3; }
                                        }
                                        description "Traffic sampling type";
                                    }

                                    leaf type {
                                        when "not(../sampling-type = 'both')";
                                        type enumeration {
                                            enum acl                            { value 1; }
                                            enum interface                      { value 2; }
                                        }
                                        description "Type of cflowd analysis";
                                    }

                                    leaf direction {
                                        type enumeration {
                                            enum ingress-only                   { value 1; }
                                            enum egress-only                    { value 2; }
                                            enum both                           { value 3; }
                                        }
                                        description "Direction of traffic for cflowd sampling";
                                    }

                                    leaf sample-profile {
                                        type union {
                                            type enumeration {
                                                enum 1                              { value 1; }
                                            }
                                            type uint32;
                                        }
                                        description "Sample profile ID";
                                    }
                                } // list sampling

                            } // container cflowd-parameters

                            container ipv4 {
                                container primary {
                                    description "Enter the primary context";

                                    leaf address {
                                        type ipv4-address;
                                        description "Primary IPv4 address assigned to the interface";
                                    }

                                    leaf prefix-length {
                                        type uint32 {
                                            range "0..32";
                                        }
                                        description "IPv4 address prefix length";
                                    }

                                }

                                list secondary {
                                    key "address";
                                    description "Enter the secondary list instance";

                                    leaf address {
                                        type ipv4-address;
                                        mandatory true;
                                        description "Secondary IPv4 address assigned to the interface";
                                    }

                                    leaf prefix-length {
                                        type uint32 {
                                            range "0..32";
                                        }
                                        mandatory true;
                                        description "IPv4 address prefix length";
                                    }
                                } // list secondary


                                list vrrp {
                                    key "virtual-router-id";
                                    description "Enter the vrrp list instance";

                                    leaf virtual-router-id {
                                        type int32 {
                                            range "1..255";
                                        }
                                        mandatory true;
                                        description "Virtual Router Identifier (VRID) for the VRRP virtual router instance";
                                    }

                                    leaf passive {
                                        type boolean;
                                        default "false";
                                        description "Suppress the processing of VRRP advertisement messages";
                                    }

                                    leaf admin-state {
                                        type admin-state;
                                        description "Administrative state of VRRP";
                                    }

                                    leaf-list backup {
                                        type inet-types:ipv4-address;
                                        max-elements 16;
                                        description "Virtual router IP addresses for the interface";
                                    }

                                    leaf priority {
                                        type uint32 {
                                            range "1..255";
                                        }
                                        description "Base priority for the VRRP";
                                    }

                                    leaf message-interval {
                                        type uint32 {
                                            range "1..2559";
                                        }
                                        units "deciseconds";
                                        default "10";
                                        description "Interval for sending VRRP advertisement messages";
                                    }

                                    leaf ping-reply {
                                        type boolean;
                                        default "false";
                                        description "Allow non-owner master to reply to ICMP echo requests";
                                    }

                                    leaf preempt {
                                        type boolean;
                                        default "true";
                                        description "Allow the VRRP to override an existing non-owner master";
                                    }

                                    leaf traceroute-reply {
                                        type boolean;
                                        default "false";
                                        description "Allow non-owner master to reply to traceroute requests";
                                    }

                                    leaf standby-forwarding {
                                        type boolean;
                                        default "false";
                                        description "Allow standby router to forward traffic";
                                    }
                                }

                                container neighbor-discovery {
                                     leaf timeout {
                                         type uint32 {
                                             range "0..65535";
                                         }
                                         units "seconds";
                                         description "Timeout for an ARP entry learned on the interface";
                                     }

                                     leaf retry-timer {
                                         type uint32 {
                                             range "1..300";
                                         }
                                         units "deciseconds";
                                         description "ARP retry interval";
                                     }

                                     leaf learn-unsolicited {
                                         type boolean;
                                         description "Learn new entries from any received NA message";
                                     }

                                     leaf proactive-refresh {
                                         type boolean;
                                         description "Send a single refresh message before entry timeout";
                                     }

                                     leaf populate {
                                         type boolean;
                                         description "Allow static and dynamic hosts to be populated in system ARP cache";
                                     }

                                     leaf local-proxy-arp {
                                        type boolean;
                                        description "Enable local proxy ARP on interface";
                                     }

                                     leaf-list proxy-arp-policy {
                                        type string;
                                        max-elements 5;
                                        ordered-by user;
                                        description "Proxy ARP policy name";
                                     }

                                     container host-route {
                                         description "Enter the host-route context";

                                         list populate {
                                             key "route-type";
                                             description "Enter the populate list instance";

                                             leaf route-type {
                                                 type enumeration {
                                                     enum "static"                       { value 1; }
                                                     enum "dynamic"                      { value 2; }
                                                     enum "evpn"                         { value 3; }
                                                 }
                                                 description "Type of ARP or ND entries that generate host routes";
                                             }

                                             leaf route-tag {
                                                 type uint32 {
                                                     range "1..255";
                                                 }
                                                 description "Tag value used with the host route from an ARP/ND entry";
                                             }
                                         }
                                     }
                                     container limit {
                                         description "Enter the limit context";

                                         leaf max-entries {
                                             type int32 {
                                                 range "0..524288";
                                             }
                                             description "Maximum number of entries learned on an IP interface";
                                         }

                                         leaf log-only {
                                             type boolean;
                                             description "Generate log entries only if limit is reached";
                                         }

                                         leaf threshold {
                                             type uint32 {
                                                 range "1..100";
                                             }
                                             units "percent";
                                             description "Threshold value that triggers a warning message";
                                         }
                                     } // container limit
                                 }

                                container bfd {
                                    description "Enter the bfd context";

                                    leaf admin-state {
                                        type admin-state;
                                        description "Administrative state of BFD sessions";
                                    }

                                    leaf transmit-interval {
                                        type uint32 {
                                            range "10..100000";
                                        }
                                        units "milliseconds";
                                        description "BFD transmit interval over this interface";
                                    }

                                    leaf receive {
                                        type uint32 {
                                            range "10..100000";
                                        }
                                        units "milliseconds";
                                        description "BFD receive interval over this interface";
                                    }

                                    leaf multiplier {
                                        type uint32 {
                                            range "1..20";
                                        }
                                        description "Number of consecutive BFD messages missed from the peer";
                                    }

                                    leaf echo-receive {
                                        type uint32 {
                                            range "100..100000";
                                        }
                                        units "milliseconds";
                                        description "Minimum echo interval over this interface";
                                    }

                                    leaf type {
                                        type enumeration {
                                            enum "cpm-np"                       { value 1; }
                                            enum "auto"                         { value 2; }
                                            enum "fp"                           { value 3; }
                                        }
                                        description "Local termination point for the BFD session";
                                    }

                                } // container bfd

                                container icmp {
                                    container redirects {
                                        description "Enter the redirects context";

                                        leaf admin-state {
                                            type admin-state;
                                            description "Administrative state of sending ICMP redirect messages";
                                        }

                                        leaf number {
                                            type uint16 {
                                                range "10..1000";
                                            }
                                            description "Maximum number of ICMP redirect messages to send";
                                        }

                                        leaf seconds {
                                            type uint16 {
                                                range "1..60";
                                            }
                                            units "seconds";
                                            description "Time used to limit the number of ICMP redirect messages";
                                        }

                                    } // container redirects

                                    container unreachables {
                                        description "Enter the unreachables context";

                                        leaf admin-state {
                                            type admin-state;
                                            description "Administrative state of sending unreachable messages";
                                        }

                                        leaf number {
                                            type uint16 {
                                                range "10..2000";
                                            }
                                            description "Maximum number of unreachable messages to send";
                                        }

                                        leaf seconds {
                                            type uint16 {
                                                range "1..60";
                                            }
                                            units "seconds";
                                            description "Time to limit the number of ICMP unreachable messages";
                                        }

                                    } // container unreachables
                                }

                                container urpf-check {
                                    presence "Enable the urpf-check context";
                                    description "Enable the urpf-check context";

                                    leaf mode {
                                        type enumeration {
                                                    enum strict                         { value 1; }
                                                    enum loose                          { value 2; }
                                                    enum strict-no-ecmp                 { value 3; }
                                                }
                                        description "Unicast RPF check mode";
                                    }

                                } // container urpf-check

                                container dhcp {
                                    leaf admin-state {
                                        type admin-state;
                                        description "Administrative state of DHCP";
                                    }
                                    leaf-list server {
                                        type ipv4-address;
                                        max-elements 8;
                                        ordered-by user;
                                        description "IP addresses for DHCP server requests";
                                    }
                                }

                            } // container ipv4

                            container sap {
                                uses sap-common:sap-details;
                                uses qos-filter-common:access-configuration-details;

                                list ip-tunnel {
                                    key "tunnel-name";
                                    max-elements 1;
                                    description "Enter the ip-tunnel list instance";

                                    leaf tunnel-name {
                                        type string;
                                        mandatory true;
                                        description "IP tunnel name";
                                    }

                                    list dest-ip {
                                        key "dest-ip-address";
                                        description "Add a list entry for dest-ip";

                                        leaf dest-ip-address {
                                            type inet-types:ip-address;
                                            description "IP address of the remote IP tunnel endpoint";
                                        }

                                    } // list dest-ip

                                    leaf remote-ip-address {
                                        type inet-types:ip-address;
                                        description "Remote IP address of the tunnel";
                                    }

                                    leaf local-ip-address {
                                        type inet-types:ip-address;
                                        description "Local IP address of this tunnel";
                                    }

                                    leaf delivery-service {
                                        type string;
                                        description "Service to originate and terminate GRE packets";
                                    }

                                    leaf ip-mtu {
                                        type uint32 {
                                            range "512..9000";
                                        }
                                        units "bytes";
                                        description "IP MTU for the interface";
                                    }

                                    leaf admin-state {
                                        type admin-state;
                                        description "Administrative state of the IP tunnel";
                                    }

                                    container gre-header {
                                        description "Enter the gre-header context";

                                        leaf admin-state {
                                            type admin-state;
                                            description "Administrative state of the GRE header in the tunnel";
                                        }
                                    }
                                }

                            } // container sap

                            container vpls {
                                description "Enter the vpls context.";

                                leaf vpls-name {
                                   type string;
                                   description "The name of the VPLS service.";
                                }

                                leaf evpn-tunnel {
                                  type boolean;
                                    default "false";
                                    description "Configure interface as VPLS EVPN tunnel.";
                                }

                                container evpn {
                                    description "Enter the evpn context.";

                                    container arp {
                                        description "Enter the arp context.";

                                        leaf learn-dynamic {
                                            type boolean;
                                            default "true";
                                            description "Enable/disable dynamic entries learning.";
                                        }

                                        leaf advertise-static {
                                            type boolean;
                                            default "false";
                                            description "Enable/disable advertise static.";
                                        }

                                        leaf advertise-static-route-tag {
                                            type uint32 {
                                                range "0..255";
                                            }
                                            default "0";
                                            description "Advertise static route tag.";
                                        }

                                        leaf advertise-dynamic {
                                            type boolean;
                                            default "false";
                                            description "Enable/disable advertise dynamic.";
                                        }

                                        leaf advertise-dynamic-route-tag {
                                            type uint32 {
                                                range "0..255";
                                            }
                                            default "0";
                                            description "Advertise dynamic route tag.";
                                        }

                                    } // container arp

                                } // container evpn

                                container egress {
                                    container routed-override-filter {
                                        leaf ip {
                                          type string;
                                          description "IPv4 filter policy name";
                                        }

                                        leaf ipv6 {
                                            type string;
                                            description "IPv6 filter policy name";
                                        }
                                    }
                                }

                                container ingress {
                                    container routed-override-filter {
                                        leaf ip {
                                            type string;
                                            description "IPv4 filter policy name";
                                        }

                                        leaf ipv6 {
                                            type string;
                                            description "IPv6 filter policy name";
                                        }
                                    }
                                }

                            } // container vpls

                            container ipv6-details {

                                container urpf-check {
                                    presence "Enable the urpf-check context";
                                    description "Enable the urpf-check context";

                                    leaf mode {
                                        type enumeration {
                                                    enum strict                         { value 1; }
                                                    enum loose                          { value 2; }
                                                    enum strict-no-ecmp                 { value 3; }
                                                }
                                        description "Unicast RPF check mode";
                                    }

                                } // container urpf-check

                                container bfd {
                                    description "Enter the bfd context";

                                    leaf admin-state {
                                        type enumeration {
                                            enum enable                         { value 1; }
                                            enum disable                        { value 2; }
                                        }
                                        description "Administrative state of BFD sessions";
                                    }

                                    leaf transmit-interval {
                                        type uint32 {
                                            range "10..100000";
                                        }
                                        units "milliseconds";
                                        description "BFD transmit interval over this interface";
                                    }

                                    leaf receive {
                                        type uint32 {
                                            range "10..100000";
                                        }
                                        units "milliseconds";
                                        description "BFD receive interval over this interface";
                                    }

                                    leaf multiplier {
                                        type uint32 {
                                            range "1..20";
                                        }
                                        description "Number of consecutive BFD messages missed from the peer";
                                    }

                                } // container bfd

                                container link-local-address {
                                    description "Enter the link-local-address context";

                                    leaf address {
                                       type inet-types:ipv6-address-no-zone;
                                        description "IPv6 link-local address";
                                    }

                                    leaf duplicate-address-detection {
                                        type boolean;
                                        description "Enable Duplicate Address Detection";
                                    }

                                } // container link-local-address

                                list ipv6 {
                                    key "ipv6-address";
                                    description "Enter the address list instance";

                                    leaf ipv6-address {
                                        type inet-types:ipv6-address-no-zone;
                                        mandatory true;
                                        description "IPv6 address assigned to the interface";
                                    }

                                    leaf prefix-length {
                                        type uint32 {
                                            range "0..128";
                                        }
                                        mandatory true;
                                        description "IPv6 address prefix length";
                                    }

                                    leaf duplicate-address-detection {
                                        type boolean;
                                        default "true";
                                        description "Enable Duplicate Address Detection";
                                    }
                                }  // list of address

                                container neighbor-discovery {
                                    description "Enter the neighbor-discovery context";

                                    leaf local-proxy-nd {
                                        type boolean;
                                        description "Enable local proxy neighbor discovery on the interface";
                                    }

                                    list static-neighbor {
                                        key "ipv6-address";
                                        description "Enter the static-neighbor list instance";

                                        leaf ipv6-address {
                                            type inet-types:ipv6-address-no-zone;
                                            description "IPv6 address corresponding to the physical address";
                                        }

                                        leaf mac-address {
                                            type string {
                                            pattern '[0-9a-fA-F]{2}(:[0-9a-fA-F]{2}){5}';
                                            }
                                            mandatory true;
                                            description "MAC address for the static neighbor";
                                        }
                                    } // list static-neighbor

                                } // container neighbor-discovery

                                list vrrp {
                                    key "virtual-router-id";
                                    max-elements 4;
                                    description "Enter the vrrp list instance";

                                    leaf virtual-router-id {
                                        type int32 {
                                            range "1..255";
                                        }
                                        description "Virtual Router Identifier (VRID) for the IP interface";
                                    }

                                    leaf-list backup {
                                        type inet-types:ipv6-address-no-zone;
                                        max-elements 4;
                                        description "Virtual router IP addresses for the interface";
                                    }

                                    leaf message-interval {
                                        type uint32 {
                                            range "10..4095";
                                        }
                                        units "centiseconds";
                                        default "100";
                                        description "Interval for sending VRRP advertisement messages";
                                    }

                                    leaf owner {
                                        type boolean;
                                        default "false";
                                        description "Designate the virtual router instance as owner";
                                    }

                                    leaf passive {
                                        type boolean;
                                        default "false";
                                        description "Suppress the processing of VRRP advertisement messages";
                                    }

                                    leaf init-delay {
                                        type uint32 {
                                            range "0..65535";
                                        }
                                        units "seconds";
                                        description "VRRP initialization delay timer";
                                    }

                                    leaf mac {
                                        type ieee-address;
                                        description "Virtual MAC address to use in ARP responses";
                                    }

                                    leaf priority {
                                        type uint32 {
                                            range "1..255";
                                        }
                                        description "Base priority for the VRRP";
                                    }

                                    leaf admin-state {
                                        type enumeration {
                                            enum enable                         { value 1; }
                                            enum disable                        { value 2; }
                                        }
                                        default "enable";
                                        description "Administrative state of VRRP";
                                    }

                                    leaf master-int-inherit {
                                        type boolean;
                                        description "Allow master instance to dictate the master down timer";
                                    }

                                    leaf ping-reply {
                                        type boolean;
                                        default "false";
                                        description "Allow non-owner master to reply to ICMP echo requests";
                                    }

                                    leaf policy {
                                        type string;
                                        description "VRRP priority control policy";
                                    }

                                    leaf preempt {
                                        type boolean;
                                        default "true";
                                        description "Allow the VRRP to override an existing non-owner master";
                                    }

                                    leaf telnet-reply {
                                        type boolean;
                                        default "false";
                                        description "Allow non-owner master to reply to Telnet requests";
                                    }

                                    leaf traceroute-reply {
                                        type boolean;
                                        default "false";
                                        description "Allow non-owner master to reply to traceroute requests";
                                    }

                                    leaf standby-forwarding {
                                        type boolean;
                                        default "false";
                                        description "Allow standby router to forward traffic";
                                    }

                                    leaf ntp-reply {
                                        type boolean;
                                        default "false";
                                        description "Allow processing of NTP requests";
                                    }

                                    leaf oper-group {
                                        type string;
                                        description "Operational group name associated with the VRRP";
                                    }

                                    leaf monitor-oper-group {
                                        type string;
                                        description "VRRP instance to follow a specified operational group";
                                    }



                                    container bfd-liveness {
                                        presence "Enable the bfd-liveness context";
                                        description "Enable the bfd-liveness context";

                                        leaf dest-ip {
                                            type inet-types:ip-address-no-zone;
                                            mandatory true;
                                            description "Destination address for the BFD session";
                                        }



                                        leaf interface-name {
                                            type string {
                                                length "1..32";
                                            }
                                            mandatory true;
                                            description "Name of the interface running BFD";
                                        }



                                    } // container bfd-liveness

                                } // list vrrp

                            } //container ipv6-details

                        } // list of interface
                    }

                    container ipv6 {
                        description "Enter the ipv6 context";

                        container router-advertisement {
                            description "Enter the router-advertisement context";

                            list interface {
                                key "ip-int-name";
                                description "Enter the interface list instance";

                                leaf ip-int-name {
                                    type string;
                                    description "VPRN interface name";
                                }

                                leaf current-hop-limit {
                                    type uint16 {
                                        range "0..255";
                                    }
                                    default "64";
                                    description "Hop limit advertised in RA messages";
                                }

                                leaf managed-configuration {
                                    type boolean;
                                    default "false";
                                    description "Set the managed address configuration flag";
                                }

                                leaf max-advertisement-interval {
                                    type uint32 {
                                        range "4..1800";
                                    }
                                    units "seconds";
                                    default "600";
                                    description "Maximum time between sending advertisement messages";
                                }

                                leaf min-advertisement-interval {
                                    type uint32 {
                                        range "3..1350";
                                    }
                                    units "seconds";
                                    default "200";
                                    description "Minimum interval between router advertisement messages";
                                }

                                leaf mtu {
                                    type uint32 {
                                        range "1280..9800";
                                    }
                                    description "MTU for sending packets to the router";
                                }

                                leaf nd-router-preference {
                                    type enumeration {
                                        enum medium                         { value 0; }
                                        enum high                           { value 1; }
                                        enum low                            { value 3; }
                                    }
                                    description "Default router preference for Router Advertisements";
                                }

                                leaf other-stateful-configuration {
                                    type boolean;
                                    default "false";
                                    description "Set the other configuration flag";
                                }

                                leaf reachable-time {
                                    type uint32 {
                                        range "0..3600000";
                                    }
                                    units "milliseconds";
                                    default "0";
                                    description "Time the router is reachable by other hosts or nodes";
                                }

                                leaf retransmit-time {
                                    type uint32 {
                                        range "0..1800000";
                                    }
                                    units "milliseconds";
                                    default "0";
                                    description "Time to advertise neighbor advertisement messages";
                                }

                                leaf router-lifetime {
                                    type uint32 {
                                        range "0|4..9000";
                                    }
                                    units "seconds";
                                    default "1800";
                                    description "Lifetime value in neighbor advertisement messages";
                                }

                                leaf admin-state {
                                    type enumeration {
                                        enum enable                         { value 1; }
                                        enum disable                        { value 2; }
                                    }
                                    default "disable";
                                    description "Administrative state of router advertisement";
                                }

                                leaf use-virtual-mac {
                                    type boolean;
                                    default "false";
                                    description "Use VRRP virtual MAC address for advertisement message";
                                }



                                container dns-options {
                                    presence "Enable the dns-options context";
                                    description "Enable the dns-options context";

                                    leaf include-rdnss {
                                        type boolean;
                                        default "true";
                                        description "Include the RDNSS option in the RA";
                                    }

                                    leaf rdnss-lifetime {
                                        type union {
                                            type int32 {
                                                range "0|4..3600";
                                            }
                                            type enumeration {
                                                enum infinite                       { value -1; }
                                            }
                                        }
                                        units "seconds";
                                        description "Maximum time over which the RDNSS address 25 is valid";
                                    }

                                    leaf-list server {
                                        type inet-types:ipv6-address-no-zone;
                                        max-elements 4;
                                        ordered-by user;
                                        description "RAs that are forwarded to IPv6 DNS servers";
                                    }



                                } // container dns-options

                                list prefix {
                                    key "ipv6-prefix";
                                    max-elements 254;
                                    description "Enter the prefix list instance";

                                    leaf ipv6-prefix {
                                        type inet-types:ipv6-prefix;
                                        description "IPv6 address prefix";
                                    }

                                    leaf autonomous {
                                        type boolean;
                                        default "true";
                                        description "Set the autonomous flag value";
                                    }

                                    leaf on-link {
                                        type boolean;
                                        default "true";
                                        description "Use prefix for on-link determination";
                                    }

                                    leaf preferred-lifetime {
                                        type union {
                                            type enumeration {
                                                enum infinite                       { value -1; }
                                            }
                                            type uint32 {
                                                range "0..4294967294";
                                            }
                                        }
                                        units "seconds";
                                        default "604800";
                                        description "Remaining time that the prefix remains preferred";
                                    }

                                    leaf valid-lifetime {
                                        type union {
                                            type enumeration {
                                                enum infinite                       { value -1; }
                                            }
                                            type uint32 {
                                                range "0..4294967294";
                                            }
                                        }
                                        units "seconds";
                                        default "2592000";
                                        description "Remaining time in which the prefix is still valid";
                                    }



                                } // list prefix

                            } // list interface

                        } // container router-advertisement

                    } // container ipv6

                    container ip-transports {
                        list ip-transport {
                            key "transport-port-id";
                            uses ip-transport-common:ip-transport-details;
                        } // // list of ip-transport
                    }

                    leaf enable-ebgp {
                        type boolean;
                        default "false";
                        description "Enable protocol eBGP";
                    }

                    container bgp-details {
                        when "../enable-ebgp= 'true'";
                        leaf loop-detect {
                            type enumeration {
                                enum "drop-peer"                    { value 1; }
                                enum "ignore-loop"                  { value 2; }
                                enum "off"                          { value 3; }
                                enum "discard-route"                { value 4; }
                            }
                            default "ignore-loop";
                            description "Strategy for loop detection in the AS path";
                        }

                        leaf peer-ip-tracking {
                            type boolean;
                            description "Enable BGP peer tracking";
                        }

                        leaf router-id {
                            type ipv4-address;
                            description "Router ID for the BGP instance in the AS";
                        }

                        container local-as {
                            description "Enter the local-as context";

                            leaf as-number {
                                type uint32 {
                                    range "1..4294967295";
                                }
                                description "Local (or virtual) BGP AS number";
                            }

                            leaf private {
                                type boolean;
                                description "Hide the local ASN in sent paths learned from peering";
                            }

                            leaf prepend-global-as {
                                type boolean;
                                description "Prepend global AS when advertising routes to BGP peer";
                            }

                        } // container local-as


                        leaf rapid-withdrawal {
                            type boolean;
                            default "false";
                            description "Send BGP withdrawal UPDATE messages immediately";
                        }

                        leaf min-route-advertisement {
                            type int16 {
                                range "1..255";
                            }
                            default "30";
                            description "Minimum time before a prefix can be advertised to peer";
                        }

                        leaf next-hop-resolution {
                            type boolean;
                            default "false";
                            description "Enable/Disable using BGP routes to resolve BGP nexthop.";
                        }

                        leaf path-mtu-discovery {
                            type boolean;
                            default "false";
                            description "Enable Path MTU Discovery";
                        }

                        leaf preference {
                            type uint32 {
                                range "1..255";
                            }
                            default "170";
                            description "Route preference for routes learned from all peers";
                        }

                        container best-path-selection {
                            description "Enter the best-path-selection context";

                            leaf compare-origin-validation-state {
                                type boolean;
                                default "false";
                                description "Specifies whether the origin validation state is used in the BGP decision process.";
                            }

                            leaf deterministic-med {
                                type boolean;
                                default "false";
                                description "Group paths based on AS before MED attribute comparison";
                            }

                            leaf origin-invalid-unusable {
                                type boolean;
                                default "false";
                                description "Specifies whether to use or ignore the routes that have an origin validation state of 'Invalid'.";
                            }

                            leaf ignore-nh-metric {
                                type boolean;
                                default "false";
                                description "Ignore next-hop distance in best path selection";
                            }

                            leaf ignore-router-id {
                                type boolean;
                                default "false";
                                description "Enter the ignore-router-id context";

                            } // container ignore-router-id

                            container always-compare-med {
                                description "Enter the always-compare-med context";

                                leaf med-value {
                                    type enumeration {
                                        enum "off"                          { value 1; }
                                        enum "missing-med-zero"             { value 2; }
                                        enum "missing-med-infinity"         { value 3; }
                                        enum "on"                           { value 4; }
                                    }
                                    default "off";
                                    description "Action for a missing MED attribute";
                                }

                                leaf strict-as {
                                    type boolean;
                                    default "true";
                                    description "Compare MED attribute from same-neighbor AS routes only";
                                }

                            } // container always-compare-med

                            container as-path-ignore {
                                description "Enter the as-path-ignore context";

                                leaf ipv4 {
                                    type boolean;
                                    default "false";
                                    description "Ignore AS path length for unlabeled unicast IPv4 routes";
                                }

                                leaf ipv6 {
                                    type boolean;
                                    default "false";
                                    description "Ignore AS path length for unlabeled unicast IPv6 routes";
                                }

                                leaf label-ipv4 {
                                    type boolean;
                                    default "false";
                                    description "Ignore AS path length for labeled-unicast IPv4 routes";
                                }

                            } // container as-path-ignore

                            container ebgp-ibgp-equal {
                                description "Enter the ebgp-ibgp-equal context";

                                leaf ipv4 {
                                    type boolean;
                                    default "false";
                                    description "Consider EBGP and IBGP IPv4 routes equal";
                                }

                                leaf ipv6 {
                                    type boolean;
                                    default "false";
                                    description "Consider EBGP and IBGP IPv6 routes equal";
                                }

                                leaf label-ipv4 {
                                    type boolean;
                                    default "false";
                                    description "Consider EBGP and IBGP label-IPv4 routes equal";
                                }

                            } // container ebgp-ibgp-equal

                        } // container best-path-selection

                        container error-handling {
                            description "Enter the error-handling context";

                            leaf update-fault-tolerance {
                                type boolean;
                                default "false";
                                description "Tolerate non-critical errors in UPDATE messages";
                            }

                        } // container error-handling

                        container graceful-restart {
                            presence "Enable the graceful-restart context";
                            description "Enable the graceful-restart context";

                            leaf restart-time {
                                type uint32 {
                                    range "0..4095";
                                }
                                default "120";
                                description "Restart time advertised by GR capability";
                            }

                            leaf stale-routes-time {
                                type uint32 {
                                    range "1..3600";
                                }
                                default "360";
                                description "Maximum time to maintain routes after graceful restart";
                            }

                            leaf gr-notification {
                                type boolean;
                                default "false";
                                description "Perform Graceful Restart procedures";
                            }

                            container long-lived {
                                presence "Enable the long-lived context";
                                description "Enable the long-lived context";

                                leaf advertised-stale-time {
                                    type uint32 {
                                        range "0..16777215";
                                    }
                                    default "86400";
                                    description "LLGR stale routes time";
                                }

                                leaf helper-override-stale-time {
                                    type uint32 {
                                        range "0..16777215";
                                    }
                                    description "Locally-configured stale routes override time";
                                }

                                leaf helper-override-restart-time {
                                    type uint32 {
                                        range "0..4095";
                                    }
                                    description "Locally-configured override for restart time";
                                }

                                leaf forwarding-bits-set {
                                    type enumeration {
                                        enum none                           { value 0; }
                                        enum all                            { value 1; }
                                        enum non-fwd                        { value 2; }
                                    }
                                    default "none";
                                    description "BGP LLGR forwarding-bit behavior for address family";
                                }

                                leaf advertise-stale-to-all-neighbors {
                                    type boolean;
                                    default "false";
                                    description "Advertise stale routes to all BGP peers";
                                }

                                leaf without-no-export {
                                    type boolean;
                                    default "false";
                                    description "Advertise LLGR stale routes to non-LLGR peers";
                                }

                                list family {
                                    key "family-type";
                                    description "Enter the family list instance";

                                    leaf family-type {
                                        type enumeration {
                                            enum ipv4                           { value 1; }
                                            enum ipv6                           { value 3; }
                                            enum flow-ipv4                      { value 10; }
                                            enum flow-ipv6                      { value 14; }
                                            enum label-ipv4                     { value 17; }
                                        }
                                        description "Address family type for LLGR";
                                    }

                                    leaf advertised-stale-time {
                                        type uint32 {
                                            range "0..16777215";
                                        }
                                        default "86400";
                                        description "LLGR stale routes time for family override";
                                    }

                                    leaf helper-override-stale-time {
                                        type uint32 {
                                            range "0..16777215";
                                        }
                                        description "Locally-configured stale routes override time";
                                    }



                                } // list family

                            } // container long-lived

                        } // container graceful-restart

                        container backup-path {
                            description "Enter the backup-path context";

                            leaf ipv4 {
                                type boolean;
                                description "Enable support for unlabeled unicast IPv4 routes";
                            }

                            leaf ipv6 {
                                type boolean;
                                description "Enable support for unlabeled unicast IPv6 routes";
                            }

                            leaf label-ipv4 {
                                type boolean;
                                description "Enable support for labeled-unicast IPv4 routes";
                            }

                            leaf label-ipv6 {
                                type boolean;
                                description "Enable support for labeled unicast IPv6 routes";
                            }

                        } // container backup-path

                        list group {
                            key "group-name";
                            description "Enter the neighbor list instance";
                            leaf group-name {
                                type string;
                                mandatory true;
                                description "Neighbor to group";
                            }

                            leaf damping {
                                type boolean;
                                description "Use BGP route damping to reduce route flap";
                            }

                            leaf authentication-key {
                                type string;
                                description "BGP authentication key for all peers";
                            }

                            leaf peer-as {
                                type uint32 {
                                    range "1..4294967295";
                                }
                                description "Peer AS number";
                            }

                            leaf peer-ip-tracking {
                                type boolean;
                                description "Enable BGP peer tracking";
                            }

                            leaf next-hop-self {
                                type boolean;
                                default "false";
                                description "Advertise routes with local address as next-hop address";
                            }

                            leaf bfd-liveness {
                                type boolean;
                                description "Enable BFD";
                            }

                            leaf split-horizon {
                                type boolean;
                                description "Prevent routes being reflected back to best-route peer";
                            }

                            leaf local-address {
                                type union {
                                    type inet-types:ip-address-no-zone;
                                    type string {
                                        length "1..32";
                                    }
                                }
                                description "Local IP address used when communicating with BGP peers";
                            }

                            list prefix-limit {
                                key "family";
                                leaf family {
                                    type enumeration {
                                        enum "ipv4"                         { value 1; }
                                        enum "ipv6"                         { value 3; }
                                        enum "mcast-ipv4"                   { value 4; }
                                        enum "flow-ipv4"                    { value 10; }
                                        enum "flow-ipv6"                    { value 14; }
                                        enum "mcast-ipv6"                   { value 16; }
                                        enum "label-ipv4"                   { value 17; }
                                    }
                                    description "Address family to which the limit applies";
                                }
                                leaf maximum {
                                    type uint32 {
                                        range "1..4294967295";
                                    }
                                    mandatory true;
                                    description "Maximum number of routes to be learned from a peer";
                                }
                                leaf threshold {
                                    type uint32 {
                                        range "1..100";
                                    }
                                    default "90";
                                    description "Percentage threshold that triggers a warning message";
                                }
                                leaf idle-timeout {
                                    type int32 {
                                        range "1..1024";
                                    }
                                    description "Time which BGP peering remains idle before reconnecting";
                                }
                            }

                            leaf admin-state {
                                type admin-state;
                                default "unlocked";
                                description "Administrative state of the BGP group";
                            }

                            container export {
                                presence "Enable the export context";
                                description "Enable the export context";
                                leaf-list policy {
                                    type string;
                                    max-elements 15;
                                    ordered-by user;
                                    description "Export policy name";
                                }
                            } // container export

                            container import {
                                presence "Enable the import context";
                                description "Enable the import context";
                                leaf-list policy {
                                    type string;
                                    max-elements 15;
                                    ordered-by user;
                                    description "Import policy name";
                                }
                            } // container export

                            container remove-private {
                                presence "Enable the remove-private context";
                                description "Enable the remove-private context";

                                leaf limited {
                                    type boolean;
                                    default "false";
                                    description "Remove private ASNs up to first public ASN encountered";
                                }

                                leaf skip-peer-as {
                                    type boolean;
                                    default "false";
                                    description "Keep private ASN if it is the same as the BGP peer ASN";
                                }

                                leaf replace {
                                    type boolean;
                                    default "false";
                                    description "Replace private ASN with global ASN before advertising";
                                }

                            } // container remove-private

                            container local-as {
                                description "Enter the local-as context";

                                leaf as-number {
                                    type uint32 {
                                        range "1..4294967295";
                                    }
                                    description "Local (or virtual) BGP AS number";
                                }

                                leaf private {
                                    type boolean;
                                    default "false";
                                    description "Hide the local ASN in sent paths learned from peering";
                                }

                                leaf prepend-global-as {
                                    type boolean;
                                    default "true";
                                    description "Prepend global ASN when advertising routes to BGP peer";
                                }

                            } // container local-as

                            leaf type {
                                type enumeration {
                                    enum "no-type"                      { value 1; }
                                    enum "internal"                     { value 2; }
                                    enum "external"                     { value 3; }
                                }
                                description "BGP peer type";
                            }

                            uses vprn:bgp-family;
                        }// list group

                        list neighbor {
                            key "ip-address";
                            description "Enter the neighbor list instance";

                           leaf-list import-policy {
                                type string {
                                    length "1..255";
                                    pattern "(.{1,64})|(.*[\\[].*)" {
                                        error-message "Policy name too long or expression not valid";
                                    }
                                }
                                description "Import policy name";
                            }

                            leaf-list export-policy {
                                type string {
                                    length "1..255";
                                    pattern "(.{1,64})|(.*[\\[].*)" {
                                        error-message "Policy name too long or expression not valid";
                                    }
                                }
                                description "Export policy name";
                            }

                            leaf ip-address {
                                type inet-types:ip-address;
                                mandatory true;
                                description "IP address that the neighbor uses to communicate with BGP peers";
                            }

                            leaf ttl-security {
                                type uint32 {
                                    range "1..255";
                                }
                                description "Minimum TTL value for an incoming BGP packet";
                            }

                            leaf bfd-liveness {
                                type boolean;
                                description "Enable BFD";
                            }

                            leaf group-name {
                                type leafref {
                                    path "../../group/group-name";
                                }
                                description "Neighbor to group";
                            }

                            leaf peer-as {
                                type uint32 {
                                    range "1..4294967295";
                                }
                                description "Peer AS number";
                            }

                            leaf admin-state {
                                type admin-state;
                                default "unlocked";
                                description "Administrative state of the BGP neighbor";
                            }

                            leaf keepalive {
                                type int32 {
                                    range "0..21845";
                                }
                                description "Time after which the BGP KEEPALIVE message is sent";
                            }

                            leaf split-horizon {
                                type boolean;
                                description "Prevent routes being reflected back to best-route peer";
                            }

                            leaf authentication-key {
                                type string;
                                description "BGP authentication key for peer";
                            }

                            leaf description {
                                type string;
                                description "Text description";
                            }

                            leaf as-override {
                                type boolean;
                                description "Replace the peer's ASN with the local ASN in AS Path";
                            }

                            leaf type {
                                type enumeration {
                                    enum "no-type"                      { value 1; }
                                    enum "internal"                     { value 2; }
                                    enum "external"                     { value 3; }
                                }
                                description "BGP peer type";
                            }

                            leaf local-preference {
                                type int64 {
                                    range "0..4294967295";
                                }
                                description "Default local preference if not in incoming routes";
                            }

                            leaf local-address {
                                type union {
                                    type ip-address;
                                    type string {
                                        length "1..32";
                                    }
                                }                                
                                description "Local IP address used when communicating with BGP peers";
                            }

                            leaf med-out {
                                type union {
                                    type uint32;
                                    type enumeration {
                                        enum igp-cost                       { value -1; }
                                    }
                                }
                                description "Default MED attribute value to advertise to peers";
                            }

                            container hold-time {
                                description "Enter the hold-time context";

                                leaf seconds {
                                    type int32 {
                                        range "0|3..65535";
                                    }
                                    description "Maximum hold time between successive messages";
                                }

                                leaf minimum-hold-time {
                                    type int32 {
                                        range "0|3..65536";
                                    }
                                    default "0";
                                    description "Minimum time BGP waits between successive messages";
                                }

                            } // container hold-time

                            container send-communities {
                                description "Enter the send-communities context";

                                leaf standard {
                                    type boolean;
                                    description "Advertise the Communities attribute to peers";
                                }

                                leaf extended {
                                    type boolean;
                                    description "Advertise the Extended Communities attribute to peers";
                                }

                                leaf large {
                                    type boolean;
                                    description "Advertise the Large Communities attribute to peers";
                                }

                            } // container send-communities

                            container remove-private {
                                presence "Enable the remove-private context";
                                description "Enable the remove-private context";

                                leaf limited {
                                    type boolean;
                                    default "false";
                                    description "Remove private ASNs up to first public ASN encountered";
                                }

                                leaf skip-peer-as {
                                    type boolean;
                                    default "false";
                                    description "Keep private ASN if it is the same as the BGP peer ASN";
                                }

                                leaf replace {
                                    type boolean;
                                    default "false";
                                    description "Replace private ASN with global ASN before advertising";
                                }

                            } // container remove-private

                            uses vprn:bgp-family;
                        }//list neighbor
                    }//container bgp-details

                    container confederation {
                        description "Enter the confederation context";

                        leaf confed-as-num {
                            type inet-types:as-number {
                                range "1..4294967295";
                            }
                            description "Confederation number within an autonomous system";
                        }

                        list members {
                            key "as-number";
                            max-elements 256;
                            description "Add a list entry for members";

                            leaf as-number {
                                type inet-types:as-number {
                                    range "1..4294967295";
                                }
                                description "Confederation AS number";
                            }

                        } // list members

                    } //container confederation

                    leaf enable-static-route {
                        type boolean;
                        default "false";
                        description "Enable protocol Static Routes";
                    }

                    container static-route-details{
                        when "../enable-static-route= 'true'";
                        list static-routes  {
                            key "ip-prefix prefix-length";
                            description "Enter the route list instance";

                            leaf ip-prefix {
                                type string;
                                mandatory true;
                                description "IP prefix for the static routes";
                            }
                            leaf prefix-length {
                                type uint32 {
                                    range "0..128";
                                }
                                mandatory true;
                                description "Prefix length for the static routes";
                            }
                            leaf route-type {
                                type enumeration {
                                    enum "unicast"                      { value 1; }
                                    enum "multicast"                    { value 2; }
                                }
                                description "Static route type";
                            }
                            leaf tag {
                                type uint32 {
                                    range "1..max";
                                }
                                description "Static route tag";
                            }
                            leaf is-blackhole {
                                type boolean;
                                default "false";
                                description "Prefix is blackhole route";
                            }

                            list next-hop {
                                key "ip-address";
                                when "../is-blackhole = 'false' ";
                                description "Enter the next-hop list instance";
                                leaf ip-address {
                                    type ip-address;
                                    mandatory true;
                                    description "IP address of the next-hop.";
                                }
                                leaf preference {
                                    type uint32 {
                                        range "1..255";
                                    }
                                    default "5";
                                    description "Priority of this static route over the routes from different sources";
                                }
                                leaf tag {
                                    type uint32 {
                                        range "1..max";
                                    }
                                    description "Static route tag";
                                }
                                leaf bfd-liveness {
                                    type boolean;
                                    default "false";
                                    description "Use Bidirectional Forwarding Detection on this static route";
                                }
                                leaf admin-state {
                                    type admin-state;
                                    default "unlocked";
                                    description "Administrative state of the static route next hop";
                                }
                            } // list next-hop

                            list indirect {
                                key "ip-address";
                                when "../is-blackhole = 'false' ";
                                description "Enter the next-hop list instance";
                                leaf ip-address {
                                    type ip-address;
                                    mandatory true;
                                    description "IP address of the next-hop.";
                                }
                                leaf preference {
                                    type uint32 {
                                        range "1..255";
                                    }
                                    default "5";
                                    description "Priority of this static route over the routes from different sources";
                                }
                                leaf tag {
                                    type uint32 {
                                        range "1..max";
                                    }
                                    description "Static route tag";
                                }
                                leaf admin-state {
                                    type admin-state;
                                    default "unlocked";
                                    description "Administrative state of the static route next hop";
                                }
                            } // list next-hop

                        } // list static-routes
                    }

                    leaf enable-isis {
                        type boolean;
                        default "false";
                        description "Enable protocol IS-IS";
                    }

                    list isis {
                        when "../enable-isis = 'true'";
                        key "isis-instance";
                        description "Enter the isis list instance";

                        leaf isis-instance {
                            type int32 {
                                range "0..127";
                            }
                            description "Instance ID for the IS-IS instance";
                        }

                        leaf admin-state {
                            type admin-state;
                            description "Administrative state of the IS-IS instance";
                        }

                        leaf-list export-policy {
                            type string;
                            max-elements 5;
                            ordered-by user;
                            description "Export policies that determine exported routes";
                        }

                        leaf-list import-policy {
                            type string;
                            max-elements 5;
                            ordered-by user;
                            description "Import policy names for routes from IGP to route table";
                        }

                        leaf level-capability {
                            type enumeration {
                                enum "1"                            { value 1; }
                                enum "2"                            { value 2; }
                                enum "1/2"                          { value 3; }
                            }
                            default "1/2";
                            description "Routing level for instance";
                        }

                        leaf advertise-router-capability {
                            type enumeration {
                                enum "area"                         { value 2; }
                                enum "as"                           { value 3; }
                            }
                            description "Router capabilities advertisement to neighbors";
                        }
                    }

                    leaf enable-ospf {
                        type boolean;
                        default "false";
                        description "Enable protocol OSPF";
                    }

                    container ospf {
                        when "../enable-ospf = 'true'";

                        leaf compatible-rfc1583 {
                            type boolean;
                            default "true";
                            description "OSPF summary and external route calculations";
                        }

                        container overload-on-boot {
                            presence "Enable the overload-on-boot context";
                            description "Enable the overload-on-boot context";

                            leaf timeout {
                                type uint32 {
                                    range "60..1800";
                                }
                                units "seconds";
                                description "Time during which the router operates in overload state before reestablishing normal operations";
                            }

                        } // container overload-on-boot

                        leaf-list export-policy {
                            type string;
                            max-elements 5;
                            ordered-by user;
                            description "Export policies that determine exported routes";
                        }

                        leaf-list import-policy {
                            type string;
                            max-elements 5;
                            ordered-by user;
                            description "Import policy names for routes from IGP to route table";
                        }

                        container timers {
                            description "Enter the timers context";

                            leaf incremental-spf-wait {
                                type uint32 {
                                    range "0..1000";
                                }
                                units "milliseconds";
                                default "1000";
                                description "Delay time before an incremental SPF calculation starts";
                            }

                            leaf lsa-accumulate {
                                type uint32 {
                                    range "0..1000";
                                }
                                units "milliseconds";
                                default "1000";
                                description "Delay to gather LSAs before advertising to neighbors";
                            }

                            leaf lsa-arrival {
                                type uint32 {
                                    range "0..600000";
                                }
                                units "milliseconds";
                                default "1000";
                                description "Min delay between receipt of same LSAs from neighbors";
                            }

                            leaf redistribute-delay {
                                type uint32 {
                                    range "0..1000";
                                }
                                units "milliseconds";
                                default "1000";
                                description "Hold down timer for external routes into OSPF";
                            }

                            container lsa-generate {
                                description "Enter the lsa-generate context";

                                leaf max-lsa-wait {
                                    type uint32 {
                                        range "10..600000";
                                    }
                                    units "milliseconds";
                                    default "5000";
                                    description "Max time between two LSAs being generated";
                                }

                                leaf lsa-initial-wait {
                                    type uint32 {
                                        range "10..600000";
                                    }
                                    units "milliseconds";
                                    default "5000";
                                    description "First wait period between OSPF LSA generation";
                                }

                                leaf lsa-second-wait {
                                    type uint32 {
                                        range "10..600000";
                                    }
                                    units "milliseconds";
                                    default "5000";
                                    description "Hold time between the first and second LSA generation";
                                }

                            } // container lsa-generate

                            container spf-wait {
                                description "Enter the spf-wait context";

                                leaf spf-max-wait {
                                    type uint32 {
                                        range "10..120000";
                                    }
                                    units "milliseconds";
                                    default "10000";
                                    description "Max interval between two consecutive SPF calculations";
                                }

                                leaf spf-initial-wait {
                                    type uint32 {
                                        range "10..100000";
                                    }
                                    units "milliseconds";
                                    default "1000";
                                    description "Initial SPF calculation delay after a topology change";
                                }

                                leaf spf-second-wait {
                                    type uint32 {
                                        range "10..100000";
                                    }
                                    units "milliseconds";
                                    default "1000";
                                    description "Hold time between the first and second SPF calculation";
                                }

                            } // container spf-wait

                        } // container timers

                        container graceful-restart {
                            presence "Enable the graceful-restart context";
                            description "Enable the graceful-restart context";

                            leaf helper-mode {
                                type boolean;
                                default "true";
                                description "Enable graceful restart helper for OSPF";
                            }

                            leaf strict-lsa-checking {
                                type boolean;
                                default "true";
                                description "Perform strict LSA checking during graceful restart helper";
                            }

                        } // container graceful-restart

                    }

                    leaf enable-rip {
                        type boolean;
                        default "false";
                        description "Enable protocol RIP";
                    }

                    container rip {
                        when "../enable-rip = 'true'";
                        leaf-list export-policy {
                            type string;
                            max-elements 5;
                            ordered-by user;
                            description "Export policies that determine exported routes";
                        }

                        leaf-list import-policy {
                            type string;
                            max-elements 5;
                            ordered-by user;
                            description "Import policy names for routes from IGP to route table";
                        }

                        leaf metric-in {
                            type uint32 {
                                range "1..16";
                            }
                            default "1";
                            description "Metric added to routes received from a RIP neighbor";
                        }

                        leaf metric-out {
                            type uint32 {
                                range "1..16";
                            }
                            default "1";
                            description "Metric added to routes exported into RIP";
                        }

                        leaf preference {
                            type uint32 {
                                range "1..255";
                            }
                            default "100";
                            description "Route preference";
                        }

                        leaf propagate-metric {
                            type boolean;
                            default "false";
                            description "Enable the BGP MED used to configure the RIP metric";
                        }

                        leaf receive {
                            type enumeration {
                                enum "version-1"                    { value 1; }
                                enum "version-2"                    { value 2; }
                                enum "both"                         { value 3; }
                                enum "none"                         { value 4; }
                            }
                            default "both";
                            description "Accepted version on received packets";
                        }

                        leaf send {
                            type enumeration {
                                enum "none"                         { value 1; }
                                enum "version-1"                    { value 2; }
                                enum "broadcast"                    { value 3; }
                                enum "multicast"                    { value 4; }
                            }
                            description "RIP version and method used to send RIP updates";
                        }

                        leaf admin-state {
                            type admin-state;
                            description "Administrative state of the IS-IS instance";
                        }

                        container timers {
                            description "Enable the timers context";

                            leaf update {
                                type uint32 {
                                    range "1..600";
                                }
                                description "Timer that controls the frequency of updates";
                            }

                            leaf timeout {
                                type uint32 {
                                    range "1..1200";
                                }
                                description "RIP timeout timer";
                            }

                            leaf flush {
                                type uint32 {
                                    range "1..1200";
                                }
                                description "RIP flush timer";
                            }

                        } // container timers

                        list group {
                            key "group-name";

                            leaf group-name {
                                type string;
                            }

                            leaf admin-state {
                                type admin-state;
                                description "Administrative state of the IS-IS group";
                            }

                            leaf-list export-policy {
                                type string;
                                max-elements 5;
                                ordered-by user;
                                description "Export policies that determine exported routes";
                            }

                            leaf-list import-policy {
                                type string;
                                max-elements 5;
                                ordered-by user;
                                description "Import policy names for routes from IGP to route table";
                            }

                            leaf metric-in {
                                type uint32 {
                                    range "1..16";
                                }
                                default "1";
                                description "Metric added to routes received from a RIP neighbor";
                            }

                            leaf metric-out {
                                type uint32 {
                                    range "1..16";
                                }
                                default "1";
                                description "Metric added to routes exported into RIP";
                            }

                            leaf preference {
                                type uint32 {
                                    range "1..255";
                                }
                                default "100";
                                description "Route preference";
                            }

                            leaf receive {
                                type enumeration {
                                    enum "version-1"                    { value 1; }
                                    enum "version-2"                    { value 2; }
                                    enum "both"                         { value 3; }
                                    enum "none"                         { value 4; }
                                }
                                default "both";
                                description "Accepted version on received packets";
                            }

                            leaf send {
                                type enumeration {
                                    enum "none"                         { value 1; }
                                    enum "version-1"                    { value 2; }
                                    enum "broadcast"                    { value 3; }
                                    enum "multicast"                    { value 4; }
                                }
                                description "RIP version and method used to send RIP updates";
                            }
                            container timers {
                                description "Enable the timers context";

                                leaf update {
                                    type uint32 {
                                        range "1..600";
                                    }
                                    description "Timer that controls the frequency of updates";
                                }

                                leaf timeout {
                                    type uint32 {
                                        range "1..1200";
                                    }
                                    description "RIP timeout timer";
                                }

                                leaf flush {
                                    type uint32 {
                                        range "1..1200";
                                    }
                                    description "RIP flush timer";
                                }

                            } // container timers

                        }

                    }
                } // list site
            }

            container sdp-details{
                list sdp {
                    key "source-device-id sdp-id";
                    description "VPRN spoke SDP information";

                    leaf source-device-id {
                        type string;
                        description "SDP Source Device Id";
                    }

                    leaf destination-device-id {
                        type string;
                        description "SDP Destination Device Id (optional - UI rendering)";
                    }

                    leaf steering-parameter {
                        type string;
                        description "Steering parameter used by Service Fulfillment";
                    }

                    leaf interface-name {
                        type string;
                        description "Layer 3 Access Interface name.";
                    }

                    leaf sdp-id {
                        type string;
                        description "SDP identifier xPath";
                    }

                    leaf description {
                        type string;
                        description "User-provided description for the SDP Bind";
                    }

                    leaf override-vc-id {
                        type boolean;
                        default "false";
                        description "Override to vc-id to user specified number";
                    }

                    leaf vc-id {
                        when "../override-vc-id='true' ";
                        type uint32 {
                            range "1..4294967295";
                        }
                        description "SDP virtual circuit identifier";
                    }
                } // container spoke-sdp
            }
        } // container vprn
   } // group configuration-details

   uses vprn:configuration-details;
}
