module qos-filter-common {
    namespace "http://www.nokia.com/management-solutions/qos-filter-common";
    prefix "qos-filter-common";
    revision "2023-08-21" {
        description
                "23.11 change";
    }
    revision "2022-03-31" {
        description
                "22.6 change - Adding none to enumeration for match-qinq-dot1p
                - Change policer-id from string to int32 ";
    }
    revision "2021-10-24" {
        description
                "21.11 changes";
    }
    revision "2021-08-18" {
        description
                "Initial revision.";
    }
    
    typedef services-sap-queuing-type {
        type enumeration {
            enum "shared"                       { value 2; }
            enum "multipoint-shared"            { value 3; }
        }
        description "The services sap ingress queuing type.";
    }
    
    typedef qos-qgrp-instance-id {
        type uint32 {
            range "1..65535";
        }
        description "The identification number of a QoS queue group instance.";
    }

    grouping access-configuration-details {
        leaf enable-qos {
            type boolean;
            default "false";
            description "Enable Access QoS";
        }

        leaf enable-filter {
            type boolean;
            default "false";
            description "Enable IP/IPv6/MAC filter";
        }
        container ingress {
            description "SAP ingress information";
            when "../enable-qos = 'true' or ../enable-filter = 'true' ";
            uses qos-filter-common:ingress-with-aggregate-policier;
        }

        container egress {
            description "SAP egress information";
            when "../enable-qos = 'true' or ../enable-filter = 'true' ";
            uses qos-filter-common:egress;
            uses qos-filter-common:agg-rate;
            uses qos-filter-common:filter;
            uses qos-filter-common:egress-vlan-manipulation;
        } // container egress
    }

    grouping aggregate-policer{
        container aggregate-policer {
            description "Enter the aggregate-policer context";

            leaf rate {
                type union {
                    type int32 {
                        range "144..1000000000";
                    }
                    type enumeration {
                        enum "max"                          { value -1; }
                    }
                }
                units "kilobps";
                description "Aggregate policer rate";
            }

            leaf burst {
                type union {
                    type int32 {
                        range "1..33292";
                    }
                    type enumeration {
                        enum "default"                      { value -1; }
                    }
                }
                description "Aggregate policer burst";
            }

            leaf cir {
                type union {
                    type int32 {
                        range "0..1000000000";
                    }
                    type enumeration {
                        enum "max"                          { value -1; }
                    }
                }
                units "kilobps";
                description "Aggregate policer CIR";
            }

            leaf cbs {
                type union {
                    type int32 {
                        range "1..33292";
                    }
                    type enumeration {
                        enum "default"                      { value -1; }
                    }
                }
                units "kilobytes";
                description "Aggregate policer CBS";
            }

        } // container aggregate-policer
    }

    grouping ingress-with-aggregate-policier{
        container qos {
            when "../../enable-qos = 'true' ";
            description "SAP ingress QoS information";

            leaf match-qinq-dot1p {
                type enumeration {
                    enum "none"                         { value 1; }
                    enum "top"                          { value 2; }
                    enum "bottom"                       { value 3; }
                }
                description "Ingress match QinQ Dot1p";
            }
            container sap-ingress {
                description "SAP ingress policy information";
                leaf queuing-type {
                    type services-sap-queuing-type;
                    description "Ingress queuing type.";
                }
                uses qos-filter-common:sap-ingress-egress;
            }
            uses qos-filter-common:qos-ingress-egress-common;
        } // container qos
        uses qos-filter-common:aggregate-policer;
        uses qos-filter-common:filter;
        uses qos-filter-common:ingress-vlan-manipulation;
        uses qos-filter-common:agg-rate;
    }

    grouping qos-vlan-egress-policy{
        container vlan-qos-policy {
            description "Enter the vlan-qos-policy context";

            leaf policy-name {
                type string;
                description "Egress vlan-qos-policy name";
            }

            leaf port-redirect {
                type boolean;
                default "false";
                description "Enable egress vlan-qos-policy port-redirect";
            }

        } // container vlan-qos-policy
        container egress-remark-policy {
            description "Enter the egress-remark-policy context";

            leaf policy-name {
                type string;
                description "Egress-remark-policy name";
            }

        } // container egress-remark-policy
}

    grouping egress {
        container qos {
            description "SAP egress QoS information";
            when "../../enable-qos = 'true' ";
            leaf qinq-mark-top-only {
                type boolean;
                description "Whether top Q-tags are marked";
            }
            container sap-egress {
                description "SAP egress policy information";
                uses qos-filter-common:sap-ingress-egress;
            }
            uses qos-filter-common:qos-ingress-egress-common;
            uses qos-filter-common:qos-vlan-egress-policy;
        } // container qos
    }

    grouping filter{
        container filter {
            description "SAP filter information";
            when "../../enable-filter = 'true' ";
            leaf ip {
                type string;
                description "IP filter identifier";
            }

            leaf ipv6 {
                type string;
                description "IPv6 filter identifier";
            }

            leaf mac {
                type string;
                description "MAC filter policy name";
            }
        } // container filter
    }

    grouping qos-ingress-egress-common {
        container policer-control-policy {
            description "Policer control policy parameters";
            leaf policy-name {
                type string;
                description "Policer control policy name";
            }

            container overrides {
                presence "Enable the overrides context";
                description "Enable the overrides context";

                container root {
                    description "Enter the root context";

                    leaf max-rate {
                        type union {
                            type int64 {
                                range "1..6400000000";
                            }
                            type enumeration {
                                enum "max"                          { value -1; }
                            }
                        }
                        description "Maximum frame-based bandwidth limit";
                    }

                    container priority-mbs-thresholds {
                        description "Enter the priority-mbs-thresholds context";

                        leaf min-thresh-separation {
                            type union {
                                type int32 {
                                    range "0..16777216";
                                }
                                type enumeration {
                                    enum "auto"                         { value -1; }
                                }
                            }
                            units "bytes";
                            description "Minimum amount of separation buffer space";
                        }

                        list priority {
                            key "priority-level";
                            description "Enter the priority list instance";

                            leaf priority-level {
                                type int32 {
                                    range "1..8";
                                }
                                description "Priority level";
                            }

                            leaf mbs-contribution {
                                type union {
                                    type int32 {
                                        range "0..16777216";
                                    }
                                    type enumeration {
                                        enum "auto"                         { value -1; }
                                    }
                                }
                                units "bytes";
                                description "Minimum amount of cumulative buffer space allowed";
                            }
                        } // list priority
                    } // container priority-mbs-thresholds
                } // container root
            } // container overrides
        } // container policer-control-policy

        container scheduler-policy {
            description "Ingress scheduler policy parameters";

            leaf policy-name {
                type string;
                description "Scheduler policy name";
            }

            container overrides {
                description "Enter the overrides context";

                list scheduler {
                    key "scheduler-name";
                    description "Enter the scheduler list instance";
                    leaf scheduler-name {
                        type string {
                            length "1..32";
                        }
                        description "Scheduler override policy name";
                    }
                    container rate {
                        description "Enter the rate context";
                        leaf pir {
                            type string;
                            description "Specifies the administrative PIR";
                        }
                        leaf cir {
                            type string;
                            description "Specifies the administrative CIR";
                        }
                    } // container rate
                    container parent {
                        description "Enter the parent context";

                        leaf weight {
                            type int32 {
                                range "0..100";
                            }
                            description "Relative weight of the scheduler to feed the queue";
                        }

                        leaf cir-weight {
                            type int32 {
                                range "0..100";
                            }
                            description "Weight used at the within-CIR port priority level";
                        }
                    } // container parent
                }//list scheduler
            } // container overrides
        } // container scheduler-policy
    }

    grouping sap-ingress-egress{

        leaf policy-name {
            type string;
            description "Sap ingress policy name.";
        }

        container overrides {
            description "SAP ingress QoS policy overrides.";

            list queue {
                key "queue-id";
                description "Ingress queue override parameters.";

                leaf queue-id {
                    type int32 {
                        range "1..32";
                    }
                    description "The unique identifier for the queue.";
                }

                leaf cbs {
                    type string;
                    description "Specify CBS.";
                }

                leaf mbs {
                    type string;
                    description "Specify MBS.";
                }
                container rate {
                    description "Enter the rate context";
                    leaf pir {
                        type string;
                        description "Specify the PIR rate.";
                    }
                    leaf cir {
                        type string;
                        description "CIR rate";
                    }
                } // container queue-rate
            } // list queue

            list policer {
                key "policer-id";
                description "Ingress policer override parameters.";

                leaf policer-id {
                    type int32;
                    description "Ingress policier id.";
                }

                leaf cbs {
                    type string;
                    description "Specify CBS.";
                }

                leaf mbs {
                    type string;
                    description "Specify MBS.";
                }

                leaf stat-mode {
                    type enumeration {
                        enum "no-stats"                     { value 0; }
                        enum "minimal"                      { value 1; }
                        enum "offered-profile-no-cir"       { value 2; }
                        enum "offered-total-cir"            { value 3; }
                        enum "offered-priority-no-cir"      { value 4; }
                        enum "offered-profile-cir"          { value 5; }
                        enum "offered-priority-cir"         { value 6; }
                        enum "offered-limited-profile-cir"  { value 7; }
                        enum "offered-profile-capped-cir"   { value 8; }
                        enum "offered-limited-capped-cir"   { value 9; }
                    }
                    description "Mode of statistics collected by the policer";
                }

                choice policer-override-rate {
                    case rate {
                        container rate {
                            description "Enter the rate context";

                            leaf pir {
                                type union {
                                    type int64 {
                                        range "1..6400000000";
                                    }
                                    type enumeration {
                                        enum "max"                          { value -1; }
                                    }
                                }
                                units "kilobps";
                                description "PIR rate";
                            }

                            leaf cir {
                                type union {
                                    type int64 {
                                        range "0..6400000000";
                                    }
                                    type enumeration {
                                        enum "max"                          { value -1; }
                                    }
                                }
                                units "kilobps";
                                description "CIR rate";
                            }

                        } // container rate

                    }
                    case percent-rate {

                        container percent-rate {
                            description "Enter the percent-rate context";

                            leaf pir {
                                type decimal64 {
                                    range "0.01..100.00";
                                    fraction-digits 2;
                                }
                                description "PIR percent rate";
                            }

                            leaf cir {
                                type decimal64 {
                                    range "0.00..100.00";
                                    fraction-digits 2;
                                }
                                description "CIR percent rate";
                            }

                        } // container percent-rate

                    }
                }
            } // list policer
        } // container overrides
    }

    grouping agg-rate{
        leaf scheduler-mode {
            type enumeration {
                enum fourPriority       { value 1; }
                enum sixteenPriority    { value 2; }
            }
        }
        choice agg-rate-or-percent-agg-rate {
            case agg-rate {
                container agg-rate {
                    description "Enter the agg-rate context";
                    leaf rate {
                        type int64 {
                            range "1..6400000000";
                        }
                        units "kilobps";
                        description "Enforced aggregate rate for all queues";
                    }
                    leaf cir {
                        type union {
                            type int32 {
                                range "0..400000000";
                            }
                            type enumeration {
                                enum "max"                          { value -1; }
                            }
                        }
                        units "kilobps";
                        default "0";
                        description "Administrative CIR";
                    }
                } // container agg-rate
            }

            case percent-agg-rate {
                container percent-agg-rate {
                    description "Enter the percent-agg-rate context";
                    leaf pir {
                        type decimal64 {
                            range "0.01..100.00";
                            fraction-digits 2;
                        }
                        description "PIR percent rate";
                    }
                    leaf cir {
                        type decimal64 {
                            range "0.00..100.00";
                            fraction-digits 2;
                        }
                        description "CIR percent rate";
                    }
                } // container percent-agg-rate
            }
        }
    }

    grouping ingress-vlan-manipulation {
        container vlan-manipulation {
            description "Enter the vlan-manipulation context";
            leaf action {
                type enumeration {
                    enum preserve                       { value 1; }
                    enum push                           { value 2; }
                    enum translate-1-to-1               { value 3; }
                    enum translate-2-to-1               { value 4; }
                    enum translate-2-to-2               { value 5; }
                }
                description "Action to manipulate the VLAN tags of the packets";
            }
            leaf outer-tag {
                type union {
                    type int32 {
                        range "0..4094";
                    }
                    type enumeration {
                        enum null                           { value -1; }
                    }
                }
                default "null";
                description "Outer VLAN tag to apply";
            }

            leaf inner-tag {
                type union {
                    type int32 {
                        range "0..4094";
                    }
                    type enumeration {
                        enum null                           { value -1; }
                    }
                }
                default "null";
                description "Inner VLAN tag to apply in case of QinQ encapsulation";
            }
        }
    }

    grouping egress-vlan-manipulation {
        container vlan-manipulation {
            description "Enter the vlan-manipulation context";
            leaf action {
                type enumeration {
                    enum preserve                       { value 1; }
                    enum push                           { value 2; }
                    enum translate-1-to-1               { value 3; }
                    enum translate-1-to-2               { value 4; }
                    enum translate-2-to-2               { value 5; }
                }
                description "Action to manipulate the VLAN tags of the packets";
            }
            leaf tag {
                type enumeration {
                    enum null                           { value -1; }
                    enum use-sap-vlan                   { value 1; }
                }
                default "null";
                description "VLAN tag to be applied by action";
            }
        }       
    }
}
