module sdp-binding-common {
    namespace "http://www.nokia.com/management-solutions/sdp-binding-common";
    prefix "sdp-binding-common";
    revision "2021-08-01" {
        description
                "Initial revision.";
    }
    
    grouping sdp-binding-details {    
    
        uses sdp-binding-common:sdp-binding-without-admin-state;

        leaf admin-state {
            type enumeration {
                 enum unlocked;
                 enum locked;
            }
            default unlocked;
            description "The desired state of this Service-SDP binding.";
        }
    }

    grouping sdp-binding-without-admin-state {

        leaf source-device-id {
            type string;
            description "SDP Source Device Id";
        }

        leaf destination-device-id {
            type string;
            description "SDP Destination Device Id (optional - UI rendering)";
        }

        leaf steering-parameter {
            type string;
            description "Steering parameter used by Service Fulfillment";
        }

        leaf sdp-id {
            type string;
            description "SDP identifier xPath";
        }

        leaf description {
            type string;
            description "User-provided description for the SDP Bind";
        }

        leaf override-vc-id {
            type boolean;
            default "false";
            description "Override to vc-id to user specified number";
        }

        leaf vc-id {
            when "../override-vc-id='true' ";
            type uint32 {
                range "1..4294967295";
            }
            description "SDP virtual circuit identifier";
        }

        leaf vlan-vc-tag {
            type uint32 {
                range "0..4094";
            }
            description "SDP bind VC tag";
        }

        leaf collect-stats {
            type boolean;
            default "false";
            description "Allow agent to collect accounting statistics";
        }

        leaf accounting-policy-id {
            type int32 {
                range "1..99";
            }
            description "The unique identifier for the Accounting policy.";
        }

        choice label {
            case entropy {
                leaf entropy-label {
                    type empty;
                    description "Enable the use of entropy labels for spoke SDPs";
                }
            }
            case hash {
                container hash-label {
                    presence "Enable the hash-label context";
                    description "Enable the hash-label context";
                    leaf signal-capability {
                        type empty;
                        description "Signal hash label capability to the remote PE";
                    }
                }
            } // container hash-label
        }
    }
}
