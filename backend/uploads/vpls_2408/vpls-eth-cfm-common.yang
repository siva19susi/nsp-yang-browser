module vpls-eth-cfm-common {
    namespace "http://www.nokia.com/management-solutions/vpls-eth-cfm-common";
    prefix "vpls-eth-cfm-common";
    revision "2021-03-15" {
        description
                "Initial revision.";
    }
    
    typedef ieee-address {
        type string {
            pattern "([0-9a-fA-F]{2}(:[0-9a-fA-F]{2}){5})|([0-9a-fA-F]{2}(-[0-9a-fA-F]{2}){5})";
        }
        description "The ieee-address type represents an IEEE 802 MAC address.";
    }
    
    grouping mep-configuration-details {    
        leaf md-admin-name {
            type string;
            description "Admin-assigned maintenance domain index value";
        }

        leaf ma-admin-name {
            type string;
            description "Admin-assigned maintenance association index value";
        }
        
        leaf mep-id {
            type uint16 {
                range "1..8191";
            }
            description "MEP identifier";
        }
        
        leaf mac-address {
            type ieee-address;
            description "MAC address for the MEP";
        }
        
        leaf one-way-delay-threshold {
            type uint32 {
                range "0..600";
            }
            description "Threshold time limit for one-way delay test";
        }
        
        leaf ccm {
            type boolean;
            description "Generate CCM messages";
        }
        
        leaf ccm-ltm-priority {
            type uint8 {
                range "0..7";
            }
            description "Priority of CCM and LTM messages transmitted by the MEP";
        }       

        leaf admin-state {
            type enumeration {
                enum unlocked;
                enum locked;
            }
            description "Service Administrative State";            
        }
        
    }    
}
