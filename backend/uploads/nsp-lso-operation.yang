module nsp-lso-operation {
  yang-version 1.1;
  namespace "urn:nokia:nsp:model:lso:operation";
  prefix nlo;

  import nsp-model-extensions {
    prefix model-ext;
  }
  import nsp-lso-manager {
    prefix nlm;
  }
  import ietf-yang-types {
    prefix yang;
  }

  organization
    "Nokia ION NSM NSP";
  contact
    "www.nokia.com";
  description
    "LSO Operation Model.";
  revision 2022-06-09 {
     description
       "Initial revision.";
       /*
        "Change the config to false for status attribute"
        */
      reference
        "revision for the release 22.6.0-rel changes.";
  }
  revision 2022-06-02 {
    description
      "Initial revision.";
      /*
      "Added Terminate execution action"
      */
     reference
       "Revision for the release 22.6.0-rel changes.";
  }
  revision 2022-05-25 {
   description
     "Initial revision.";
  /*
 "Changes in this revision:
  Added the following changes to support rollback feature :
     Added action 'rollback-execution' at phase
     Added 'action-mode' at execution and execution-stage 
  Added the following changes to support rerun feature  
    Added action 'rerun-execution' at phase
    removed status 'deprecated' for 're-run-count' at execution
  Added rpc 'get-phases-from-in-use-profile' to get phase details from InUseProfile
     
     
  */
   reference
     "Revision for the release 22.6.0-rel changes.";
 }
 revision 2022-02-10 {
   description
     "Initial revision.";
  /*
 "Changes in this revision:
  Added parent-operation to support cloning
  */
   reference
     "Revision for the release 22.6.0-rel changes.";
 }
 revision 2022-04-22 {
   description
     "Initial revision";
   /*
   "Changes in this revision:
    Added start-operation Action
    */
      reference
        "Revision for the release 22.6.0.rel changes.";
 }
 revision 2022-02-02 {
   description
     "Initial revision.";
   /*
 "Changes in this revision:
   Added Pause and resume Action
  */
   reference
     "Revision for the release 22.6.0-rel changes.";
 }

 revision 2021-11-18 {
    description
      "Revision for the release 21.11.0-rel changes.";
    /*
    "Changes in this revision:
      Changed GetOperationByNeNameAndCategoryAndStatus
     */
    reference
      "";
  }

 revision 2021-12-10 {
    description
      "Revision for the release 22.6.0-rel changes.";
    /*
    "Changes in this revision:
      Added new attributes is-awaiting-user-input,scheduled-phases,total-phases, number-of-successful-execution
     */
    reference
      "";
  }
  revision 2021-08-11 {
    description
      "NSP 21.11 release changes.";
    /*
    "Changes in this revision:
     Added the following changes to support phasing feature :
      - Defined enum 'phase-exec-mode'
      - Added list 'phase' in 'operation' and phase actions 'start' and 'stop'
      - Added leaf 'phase-name' in 'execution'
      - Deprecated execution's action 'retry-execution' and operation's action 'retry-failed-executions'
      - Added new operation action 'stop'.
     Following changes as part of execution control feature :
      - Use group 'execution-control-parameters' in 'operation'
      - Use group 'execution-control-parameters' in 'phase'
     */
    reference
      "";
  }
  revision 2021-05-21 {
    description
      "Revision for the release 21.6.0-rel changes.";
    /*
    "Changes in this revision:
     Deprecated the following leaves in the list execution:
     - current-stage
     */
    reference
      "";
  }
  revision 2020-06-25 {
    description
      "Initial revision.";
    reference
      "";
  }

  typedef phase-exec-mode {
    type enumeration {
      enum immediate {
        value 0;
        description
          "Indicates immediate phase execution.";
      }
      enum manual {
        value 1;
        description
          "Indicates manual phase execution.";
      }
      enum schedule {
        value 2;
        description
          "Indicates the phase execution is scheduled.";
      }
    }
    description
      "Indicates the mode of the phase execution.";
  }

  container lso-operations {
    description
      "LSO operations.";
    list operation {
      model-ext:custom-impl "java" {
        model-ext:class "com.nokia.nsp.lsom.operation.transaction.OperationTransactionHandler";
      }
      model-ext:table-name "operation";
      key "operation-type name";
      description
        "List of operations.";
      leaf operation-type {
        type leafref {
          path "/nlm:lso-manager/nlm:operation-types/nlm:operation-type/nlm:name";
        }
        description
          "Name of the operation-type (for example: ne-backup).";
      }
      leaf name {
        type string{
          pattern '[^\\/]*';
        }
        description
          "Name of the operation.";
      }
      leaf description {
        type string;
        description
          "Description of the operation (for example: NE Backup for SR).";
      }
      leaf category {
        type nlm:operation-category; 
        config false;
        description
          "Category of the operation-type.";
      }
      leaf created-by {
        type string;
        config false;
        description
          "Author of the operation.";
      }
      leaf creation-time {
        type yang:date-and-time;
        config false;
        description
          "Indicates the date and time when the operation was created.";
      }
      leaf start-time {
        type yang:date-and-time;
        config false;
        description
          "Indicates the date and time when the operation will start running.";
      }
      leaf last-modified-time {
        type yang:date-and-time;
        config false;
        description
          "Indicates the date and time when the operation was last modified.";
      }
      leaf end-time {
        type yang:date-and-time;
        config false;
        description
          "Indicates the date and time when the operation got completed.";
      }
      leaf status {
        type string;
        config false;
        description
          "Indicates the status of the operation. Supported values are Saved, Not-Started, Running, Success, Partially-Success and Failed.";
      }
      leaf-list target {
        type string;
        description
          "List of targets. Target can be NetworkElementGroup or NetworkElement.";
      }
      leaf is-scheduled {
        type boolean;
        config false;
        status deprecated;
        description
          "Indicates if operation is a scheduled one. It will be true if and only if it is a single phase scheduled operation. This flag is not used for phase level schedules(Multiphase operation).";
      }
      leaf schedule {
        type string;
        config false;
        description
          "Name of the scheduler that created the operation.";
      }
      leaf repeats {
        type string;
        config false;
        description
          "Indicates frequency of schedule.";
      }
      leaf additional-info {
        type string;
        config false;
        description
          "Additional information.";
      }
      leaf re-run-count {
        type uint16;
        config false;
        status deprecated;
        description
          "Total re run count.";
      }
      leaf total-executions {
        type uint32;
        config false;
        default 0;
        description
          "Total number of executions spanned by the operation.";
      }
      leaf internal {
        type boolean;
        default "false";
        config false;
        description
          "Indicates if the operation is of internal operation-type.";
      }
      leaf threshold-crossed {
        type boolean;
        default "false";
        config false;
        description
          "Indicates if the threshold has been reached. If true then stops the submission of executions further.";
      }
      leaf current-phase {
        type leafref {
          path "../phase/name";
        }
        config false;
        description
          "This is the current phase in-progress or the next phase to be started. If a phase completes with all failed executions then current phase will point to that.";
      }
      leaf profile-id {
        type uint64;
        config false;
        description
          "In use profile identifer.";
      }
      leaf stopped {
        type boolean;
        default "false";
        config false;
        description
          "True Indicates that a stop Action was performed on the Operation";
      }
      leaf is-awaiting-user-input  {
        type boolean;
        default "false";
        config false;
        description
          "True Indicates that a current phase execution mode is manual";
      }
      leaf scheduled-phases  {
        type uint32;
        config false;
        description
          "Number of Scheduled phases.";
      }
      leaf total-phases  {
        type uint32;
        config false;
        description
          "Total number of phases in the operation.";
      }
      leaf number-of-successful-execution  {
        type uint32;
        config false;
        description
          "Total number of successful execution";
      }
      leaf paused-status {
        type string;
        config false;
        description
          "Indicates the pause status of the operation. Supported values are Manual-pause, Automatic-pause, Threshold-pause";
      }
      leaf parent-operation {
        type string;
        description
          "Indicates the parent operation for the cloned operation";
      }
      leaf last-pause-time {
        type string;
        config false;
        description
          "Indicates the last pause time";
      }
      leaf is-auto-run {
        type boolean;
        default "true";
        description
           "True Indicates that it should run the operation directly";
      }

      uses nlm:execution-control-parameters-global;
      list target-info {
        model-ext:table-name "operation_target_info";
        key "id";
        config false;
        ordered-by user;
        description
          "List of Target info";
        leaf id {
          type string;
          description
            "Auto generated Id for Target Info";
        }
        leaf ne-id {
          type string;
          description
            "Id of the Network Element";
        }
        leaf ne-name {
          type string;
          description
            "Name of the Target";
        }
        leaf identifier {
          type string;
          description
            "Identifier of the Target";
        }
        leaf group {
          type string;
          description
            "Group that this Target Belong to.";
        }
      }
      list phase {
        model-ext:custom-impl "java" {
          model-ext:class "com.nokia.nsp.lsom.phase.transaction.PhaseTransactionHandler";
        }
        model-ext:table-name "phase";
        key "name";
        ordered-by user;
        description
          "List of the phase information.";
        leaf name {
          type string;
          description
            "Name of the phase.";
        }
        leaf execution-mode {
          type phase-exec-mode;
          description
            "Phase execution mode. It can be immediate, manual or scheduled.";
        }
        leaf time-zone {
          type string;
          description
            "Indicates the time zone that phase schedule should run on.";
        }
        leaf schedule-start-time {
          type yang:date-and-time;
          description
            "Phase Schedule start time.";
        }
        leaf schedule-end-time {
          type yang:date-and-time;
          description
            "Phase Schedule end time.";
        }
        leaf start-time {
          type yang:date-and-time;
          config false;
          description
            "Indicates the date and time when the phase will start running.";
        }
        leaf last-modified-time {
          type yang:date-and-time;
          config false;
          description
            "Indicates the date and time when the operation was last modified.";
        }
        leaf end-time {
          type yang:date-and-time;
          config false;
          description
            "Indicates the date and time when the operation got completed.";
        }
        leaf status {
          type string;
          default "Not-Started";
          config false;
          description
            "Status of the phase.complete, scheduled, paused, Failed";
        }
        leaf additional-info {
          type string;
          config false;
          description
            "Additional information.";
        }
        leaf threshold-crossed {
          type boolean;
          default "false";
          config false;
          description
            "Indicates if the threshold has been reached. If true then stops the submission of executions further.";
        }
        leaf timedout {
          type boolean;
          default "false";
          config false;
          description
            "Indicates if the timeout happend. If true then stops the submission of executions further.";
        }
        leaf stopped {
          type boolean;
          default "false";
          config false;
          description
            "True Indicates that a stop Action was performed on the Phase";
        }
        
        uses nlm:execution-control-parameters;
        action start {
          description
            "Starts the phase execution.";
          model-ext:operation "java" {
            model-ext:class "com.nokia.nsp.lsom.phase.action.StartPhaseExecutionActionImpl";
          }
        }
        action stop {
          description
            "Stops the phase execution.";
          model-ext:operation "java" {
            model-ext:class "com.nokia.nsp.lsom.phase.action.StopPhaseExecutionActionImpl";
          }
        }
        action recovery {
          description
            "Recovers if phase is dormant in In-Progress state for longer duration.";
          model-ext:operation "java" {
            model-ext:class "com.nokia.nsp.lsom.execution.action.PhaseRecoveryActionImpl";
          }
        }
        action rerun-execution {
          description
            "action to RollBack the execution.";
          model-ext:operation "java" {
            model-ext:class "com.nokia.nsp.lsom.execution.action.ReRunFailedExecutionActionImpl";
          }
          input {
            leaf-list executions {
              type string;
              config false;
              description
                "List of executions which need to be rerun.";
            }
           
          }
        }
        action rollback-execution {
          description
            "action to RollBack the execution.";
          model-ext:operation "java" {
            model-ext:class "com.nokia.nsp.lsom.execution.action.RollBackActionImpl";
          }
          input {
            leaf-list executions {
              type string;
              config false;
              description
                "List of executions which need to be roll back.";
            }
           
          }
		}
        action terminate-execution {
          description
            "action to terminate the execution.";
             model-ext:operation "java" {
               model-ext:class "com.nokia.nsp.lsom.execution.action.TerminateExecutionActionImpl";
             }
          input {
            leaf-list executions {
              type string;
              config false;
              description
                "List of executions which need to terminate.";
              }
          }
		}
      }
      container executions {
        config false;
        description
          "List of executions triggered by the operation.";
        list execution {
          model-ext:table-name "execution";
          key "name";
          description
            "List of the execution";
          leaf name {
            type string;
            description
              "Name of the execution.";
          }
          leaf phase-name {
            type string;
            description
              "Name of the phase to which execution belongs to.";
          }
          leaf workflow-name {
            type string;
            description
              "Name of the parent workflow";
          }
          leaf workflow-execution-id {
            type string;
            description
              "UUID of the workflow execution.";
          }
          leaf product {
            type string;
            description
              "NE product type.";
          }
          leaf ne-name {
            type string;
            description
              "NE Name.";
          }
          leaf creation-time {
            type yang:date-and-time;
            description
              "Execution creation time.";
          }
          leaf start-time {
            type yang:date-and-time;
            description
              "Execution start time.";
          }
          leaf last-modified-time {
            type yang:date-and-time;
            description
              "Last updated time of the execution.";
          }
          leaf end-time {
            type yang:date-and-time;
            description
              "Execution end time.";
          }
          leaf current-stage {
            type string;
            status deprecated;
            description
              "Current stage of the execution.";
          }
          leaf status {
            type string;
            description
              "Status of the execution. Possible values are Initializing, Idle, Running, Paused, Success, Error, Cancelled.";
          }
          leaf additional-info {
            type string;
            description
              "Additional information.";
          }
          leaf re-run-count {
            type uint16;
            default 0;
            description
              "Total re run count of an execution.";
          }
          leaf is-custom-stage-defined {
            type boolean;
            default "false";
            description
              "True if custom stage is defined by the user.";
          }
          leaf action-mode {
            type nlm:mode;
            default "normal";
            description
              "specifies the mode of action on execution";
          }
          container execution-stages {
            description
              "List of execution stages performed by this operation.";
            list stage {
              model-ext:table-name "execution_stages";
              key "workflow-name name task-id";
              ordered-by user;
              description
                "List of stages.";
              leaf name {
                type string;
                description
                  "Name of the stage as defined in workflow.";
              }
              leaf status {
                type string;
                description
                  "Status of the execution. Possible values are Running, Success, Error and Cancelled.";
              }
              leaf start-time {
                type yang:date-and-time;
                description
                  "Start time of the stage execution.";
              }
              leaf end-time {
                type yang:date-and-time;
                description
                  "End time of the the stage execution";
              }
              leaf additional-info {
                type string;
                description
                  "Additional information.";
              }
              leaf workflow-name {
                type string;
                description
                  "Name of the workflow that the task/stage belongs to.";
              }
              leaf workflow-execution-id {
                type string;
                description
                  "Workflow execution id.";
              }
              leaf task-id {
                type string;
                description
                  "Task id.";
              }
              leaf action-mode {
                type nlm:mode;
                default "normal";
                description
                  "specifies the mode of action on execution";
              }
            }
          }
          action retry-execution {
            description
              "Re runs the failed execution.";
            model-ext:operation "java" {
              model-ext:class "com.nokia.nsp.lsom.execution.action.ReRunFailedExecutionActionImpl";
            }
          }
          action recovery {
            description
              "Recovers if execution is dormant for longer duration.";
            model-ext:operation "java" {
              model-ext:class "com.nokia.nsp.lsom.execution.action.ExecutionRecoveryActionImpl";
            }
          }
          action delete-execution {
            description
              "Deletes the completed execution.";
            model-ext:operation "java" {
              model-ext:class "com.nokia.nsp.lsom.execution.action.DeleteExecutionActionImpl";
            }
          }
         
        
        }
      }
      action recovery {
        description
          "Recovers if operation is dormant for longer duration.";
        model-ext:operation "java" {
          model-ext:class "com.nokia.nsp.lsom.operation.action.OperationRecoveryActionImpl";
        }
      }
      action retry-failed-executions {
        status deprecated;
        description
          "Re runs the failed operation.";
        model-ext:operation "java" {
          model-ext:class "com.nokia.nsp.lsom.operation.action.ReRunFailedOperationActionImpl";
        }
      }
      action execution-count-by-status {
        description
          "Gives execution count for each status along with the total count.";
        model-ext:operation "java" {
          model-ext:class "com.nokia.nsp.lsom.operation.action.ExecutionsCountByStatusActionImpl";
        }
        input {
          leaf phase-name {
            type leafref {
              path "/lso-operations/operation/executions/execution/phase-name";
            }
            description
              "Name of the phase for which execution counts by status needed.";
          }
        }
        output {
          list phase-execution-count {
            description
              "List of phases.";
            leaf phase-name {
              type string;
              description
                "Name of the stage as defined in workflow.";
            }
            leaf init-count {
              type uint32;
              status deprecated;
              description
                "The number of executions in initialization state.";
            }
            leaf idle-count {
              type uint32;
              status deprecated;
              description
                "The number of executions in idle state.";
            }
            leaf not-started-count {
              type uint32;
              description
                "The number of executions in idle state.";
            }
            leaf running-count {
              type uint32;
              description
                "The number of executions currently in-progress.";
            }
            leaf success-count {
              type uint32;
              description
                "The number of executions completed successfully.";
            }
            leaf cancelled-count {
              type uint32;
              status deprecated;
              description
                "The number of executions cancelled.";
            }
            leaf paused-count {
              type uint32;
              status deprecated;
              description
                "The number of executions in paused state.";
            }
            leaf failed-count {
              type uint32;
              description
                "The number of executions failed.";
            }
            leaf total-count {
              type uint32;
              description
                "The total number of executions.";
            }
          }
        }
      }
      action stop {
        description
          "Stops the running operation. Marks it as completed. All Not-Started executions will be marked Failed and In-Progress executions will continue to completion.";
        model-ext:operation "java" {
          model-ext:class "com.nokia.nsp.lsom.operation.action.StopOperationExecutionActionImpl";
        }
      }
      action pause-operation {
        description
          "Pause the In-Progress Operation ";
        model-ext:operation "java" {
          model-ext:class "com.nokia.nsp.lsom.operation.action.PauseOperationActionImpl";
         }
       }
       action resume-operation {
         description
           "Resume the Paused Operation";
         model-ext:operation "java" {
           model-ext:class "com.nokia.nsp.lsom.operation.action.ResumeOperationActionImpl";
          }
          input {
          	leaf rerun {
              type boolean;
               description
                 "Specifies whether to re run the failed executions as part of resume action.";
          }
        }
      }
      action start-operation  {
        description
          "Start the Saved Operation";
        model-ext:operation "java" {
          model-ext:class "com.nokia.nsp.lsom.operation.action.StartOperationFromSavedActionImpl";
        }
      }
    }
  }
  rpc operation-count-per-status {
    description
      "Gives operation count for each status along with the total count.";
    model-ext:operation "java" {
      model-ext:class "com.nokia.nsp.lsom.operation.rpc.OperationCountByStatusRpcImpl";
    }
    output {
      leaf not-started-count {
        type uint32;
        description
          "The number of operations in Not-Started state.";
      }
      leaf running-count {
        type uint32;
        description
          "The number of operations in Running state.";
      }
      leaf completed-count {
        type uint32;
        description
          "The number of operations in Running state.";
      }
      leaf success-count {
        type uint32;
        status deprecated;
        description
          "The number of operations in Success state.";
      }
      leaf partially-success-count {
        type uint32;
        status deprecated;
        description
          "The number of operations in Partially-Success state.";
      }
      leaf failed-count {
        type uint32;
        status deprecated;
        description
          "The number of operations in Failed state.";
      }
      leaf total-count {
        type uint32;
        description
          "The total number of operations.";
      }
    }
  }

  rpc get-executions-by-ne-name {
    description
      "Gives list of executions for a specific NE name.";
    model-ext:operation "java" {
      model-ext:class "com.nokia.nsp.lsom.operation.rpc.GetExecutionsByNeNameRpcImpl";
    }
    input {
      leaf ne-name {
        type string;
        description
          "Name of the NE.";
      }
    }
    output {
      list execution {
        description
          "The total number of operations.";
        leaf name {
          type string;
          description
            "Name of the execution.";
        }
        leaf operation-type {
          type leafref {
            path "/nlm:lso-manager/nlm:operation-types/nlm:operation-type/nlm:name";
          }
          description
            "Name of the operation-type.";
        }
        leaf operation-name {
          type string;
          description
            "Name of the operation.";
        }
        leaf created-by {
          type string;
          description
            "Author of the operation.";
        }
        leaf category {
          type leafref {
            path "/nlm:lso-manager/nlm:operation-types/nlm:operation-type/nlm:category";
          }
          description
            "Category of the operation-type.";
        }
        leaf start-time {
          type yang:date-and-time;
          description
            "Start time of the execution.";
        }
        leaf end-time {
          type yang:date-and-time;
          description
            "End time of the execution.";
        }
        leaf status {
          type string;
          description
            "Status of the execution.";
        }
        leaf workflow-name {
          type string;
          description
            "Name of the parent workflow.";
        }
        leaf workflow-execution-id {
          type string;
          description
            "UUID of the workflow execution.";
        }
      }
    }
  }

  rpc get-operation-by-ne-name-and-category {
    description
      "Gives list of executions for a specific NE.";
    model-ext:operation "java" {
      model-ext:class "com.nokia.nsp.lsom.operation.rpc.GetOperationByNeNameAndCategory";
    }
    input {
      leaf ne-name {
        type string;
        description
          "Name of the NE";
      }
      leaf category {
        type leafref {
          path "/nlm:lso-manager/nlm:operation-types/nlm:operation-type/nlm:category";
        }
        description
          "Category of the operation-type";
      }
    }
    output {
      anydata data {
        description
          "Copy of the data subset that matched
           the filter (if any).  An empty data container
           indicates that the request did not produce any results.";
      }
    }
  }

  rpc get-operation-by-ne-name-and-category-and-status {
    description
      "Gives list of executions for a specific NE.";
    model-ext:operation "java" {
      model-ext:class "com.nokia.nsp.lsom.operation.rpc.GetOperationByNeNameAndCategoryAndStatus";
    }
    input {
      leaf ne-name {
        type string;
        description
          "Name of the NE";
      }
      leaf category {
        type leafref {
          path "/nlm:lso-manager/nlm:operation-types/nlm:operation-type/nlm:category";
        }
        description
          "Category of the operation-type";
      }
      leaf status {
        type string;
        description
          "Status of the operation-type";
      }
    }
    output {
      anydata data {
        description
          "Copy of the data subset that matched
                  the filter (if any).  An empty data container
                  indicates that the request did not produce any results.";
      }
    }
  }
  rpc get-target-software-version {
    description
      "Gives list of images for a specific NE.";
    model-ext:operation "java" {
      model-ext:class "com.nokia.nsp.lsom.operation.rpc.GetTargetSoftwareVersion";
    }
    output {
      anydata data {
        description
          "Copy of the data subset that matched
                  the filter (if any).  An empty data container
                  indicates that the request did not produce any results.";
      }
    }
  }

  rpc get-nsp-ne-sw-import-ne-families {
    description
      "Gives list of NE families for a ne-sw-import.";
    model-ext:operation "java" {
      model-ext:class "com.nokia.nsp.lsom.operation.rpc.GetNeSwImportNeFamilies";
    }
    input {
      leaf operation-type {
      type string;
      description
      "Operation type";
      }
    }
    output {
      anydata data {
        description
          "Copy of the data subset that matched
                  the filter (if any).  An empty data container
                  indicates that the request did not produce any results.";
      }
    }
  }
  rpc get-fdn-details-from-target-info  {
    description
      "Gives the list of target fdn details";
    model-ext:operation "java" {
      model-ext:class "com.nokia.nsp.lsom.operation.rpc.GetFdnDetailsFromTargetInfo";
    }
    input {
      leaf operation-type {
      type string;
      description
      "Operation type";
      }
      leaf name {
      type string;
      description
      "Operation name";
      }
    }
    output {
      anydata data {
        description
          "...";
      }
    }
  }
  
  rpc get-phases-from-in-use-profile {
    description
      "Gives list of phases from inUseProfile .";
    model-ext:operation "java" {
      model-ext:class "com.nokia.nsp.lsom.operation.rpc.GetPhasesFromInUseProfile";
    }
    input {
      leaf name {
        type string;
        description
          "Name of the operation.";
      }
	  leaf operation-type {
        type string;
        description
          "Name of the operation type.";
      }
    }
    output {
      list phases {
        description
          "List of Phases in the profile.";
        leaf name {
          type string;
          description
            "Name of the phase.";
        }
        leaf description {
          type string;
          description
            "Description of phase.";
        }
        leaf concurrency-count {
          type string;
          description
            "Concurrency count of the phase.";
        }
        leaf average-execution-time-threshold {
          type string;
		  description
            "Average execution time.";
        }
        leaf phase-timeout {
          type string;
          description
			"The phase timeout.";
        }
        leaf rollback-allowed {
          type boolean;
          description
            "Start time of the execution.";
        }
        
      }
    }
  }
  
}
