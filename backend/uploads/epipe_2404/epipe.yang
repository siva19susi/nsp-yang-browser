module epipe {
    namespace "urn:nokia:nsp:model:nsp-service-intent:services:epipe";
    yang-version 1.1;
    prefix "epipe";
    import qos-filter-common { prefix "qos-filter-common"; }
    import sdp-binding-common { prefix "sdp-binding-common"; }
    import sap-common { prefix "sap-common"; }
    import svc-common { prefix "svc-common"; }
    organization "NOKIA Corp";
    contact "";
    description "";
    revision "2022-04-29" {
        description
                "22.6 changes - Remove pw-switching";
    }
    revision "2021-08-25" {
        description
                "21.11 changes";
    }
    revision "2021-06-15" {
        description
                "Initial revision.";
    }
    typedef ieee-address {
        type string {
            pattern "([0-9a-fA-F]{2}(:[0-9a-fA-F]{2}){5})|([0-9a-fA-F]{2}(-[0-9a-fA-F]{2}){5})";
        }
        description "The ieee-address type represents an IEEE 802 MAC address.";
    }
    
    grouping configuration-details {
        container epipe {
            leaf ne-service-id {
                type uint32 {
                    range "1..2147483647";
                }
                description "Specify NE Service Id";
            }

            leaf mtu {
                type uint16;
                description "Service MTU";
            }

            uses svc-common:svc-details;

            container site-a {

                uses svc-common:site-details;

                list endpoint {
                    key "port-id inner-vlan-tag outer-vlan-tag";
                    max-elements 2;

                    uses sap-common:sap-details;
                    uses qos-filter-common:access-configuration-details;
                }

            }

            container site-b{

                uses svc-common:site-details;

                list endpoint {
                    key "port-id inner-vlan-tag outer-vlan-tag";
                    max-elements 2;
                    
                    uses sap-common:sap-details;  
                    uses qos-filter-common:access-configuration-details;
                }  


            }

            container sdp-details{
                list sdp {
                    key "source-device-id sdp-id";
                    max-elements 12;
                    description "EPIPE spoke SDP information";

                    uses sdp-binding-common:sdp-binding-details;

                    leaf vc-type {
                        type enumeration {
                            enum "ether"                        { value 2; }
                            enum "vlan"                         { value 4; }
                        }
                        default "ether";
                        description "Type of virtual circuit (VC) associated with the SDP binding";
                    }
                    leaf control-word {
                        type boolean;
                        default "false";
                        description "Use the control word as preferred";
                    }
                } // list spoke-sdp
            }
        }
   }
   uses epipe:configuration-details;
}
