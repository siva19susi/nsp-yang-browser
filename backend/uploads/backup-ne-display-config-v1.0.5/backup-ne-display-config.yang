module backup-ne-display-config {
  yang-version 1.1;
  namespace "urn:nokia:nsp:model:lso:operation:backup-ne-display-config";
  prefix ping;

  import nsp-lso-operation {
    prefix nlo;
  }

  organization "Nokia";
  contact "";
  description "NSP Operation Manager - Backup NE Display Config";

  revision 2024-01-25 {
    description "version 1";
    reference "";
  }

  augment "/nlo:lso-operations/nlo:operation" {
    when "operation-type='backup-ne-display-config'";
    description "Augmentation of operation input";
  }

  augment "/nlo:lso-operations/nlo:operation/nlo:executions/nlo:execution" {
    when "../../operation-type='backup-ne-display-config'";
    description "Augmentation of operation execution state data";
    container backup-ne-display-config-execution {
      description "State data container for backup execution.";
      leaf backupFilePath {
        type string;
        description "Indicates the backup file path created in the NSP";
      }
    }
  }
}
