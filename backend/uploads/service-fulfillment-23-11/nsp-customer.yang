module nsp-customer {
    yang-version 1.1;
    namespace "urn:nokia:nsp:model:customers";
    prefix "customers";
    import nsp-model-extensions { prefix model-ext; }
    organization "Nokia";
    contact
        "Nokia NSP Support
         Web: <http://www.nokia.com>";
    description "Adds customer configuration model";
    revision "2023-05-31" { description "Include sources and add customer sites"; }
    revision "2022-11-20" { description "bulk-associate"; }
    revision "2022-11-16" { description "Add auto-associate"; }
    revision "2021-08-30" { description "customer configuration"; }

    model-ext:include-sources true;

    container customers {
        list customer {
            key "id";
            leaf id {
                type int32;
                description "The customer's identifier.";
            }
            leaf name {
                type string;
                description "The customer's name.";
            }
            leaf description {
                type string;
                description "The customer's description.";
            }
            leaf phone-number {
                type string;
                description "The customer's phone number.";
            }
            leaf contact {
                type string;
                description "The customer's contact.";
            }
            leaf address {
                type string;
                description "The customer's address.";
            }
            leaf email {
                type string;
                description "The customer's email.";
            }
            leaf bulk-associate {
                type boolean;
                description "The customer supports bulk associating templates to the service.";
                default "false";
            }

            list sites {
                key "site-id";
                leaf site-id {
                    type string;
                    description "The customer site identifier.";
                }
                leaf name {
                    type string;
                    description "The customer's name.";
                }
                leaf description {
                    type string;
                    description "The customer's description.";
                }
                leaf phone-number {
                    type string;
                    description "The customer's phone number.";
                }
                leaf contact {
                    type string;
                    description "The customer's contact.";
                }
            }
        }
    }
}
