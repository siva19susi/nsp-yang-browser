module template-common {
    yang-version 1.1;
    namespace "urn:nokia:nsp:model:template-common";
    prefix "template-common";

    import service-extension-common-types { prefix "svc-common-types"; }
    organization "Nokia";
    contact
        "Nokia NSP Support
         Web: <http://www.nokia.com>";
    description "Adds template common";
    revision "2023-06-27" { description "Move to extension common"; }
    revision "2022-10-10" { description "template-report-info"; }
    revision "2021-07-20" { description "template configuration"; }

    typedef workflow-case {
        type enumeration {
            enum success    { value 0; }
            enum fail       { value 1; }
        }
        description "Specifies the workflow case.";
    }
    typedef state {
        type enumeration {
            enum draft          { value 0; }
            enum released       { value 1; }
         }
         description "Specifies the template's state.";
    }
    grouping template {
        leaf name {
            type string;
            description "The template name.";
        }
        leaf description {
            type string;
            description "The template description.";
        }
        leaf intent-type { //TODO leaf-ref from catalogue
            type string;
            description "The intent type.";
        }
        leaf intent-version { //TODO leaf-ref from catalogue
            type int32;
            description "The intent version.";
        }
        leaf state {
            type state;
            description "The life cycle state of the template.";
        }
        leaf ui-config {
            type string;
            description "The ui config file name.";
        }
        uses svc-common-types:user-timestamp;
        list workflows {
            key "service-lifecycle-state service-lifecycle-case";

            leaf service-lifecycle-state {
                type svc-common-types:olc;
                description "The Service Lifecycle state for which to run the workflow.";
            }
            leaf service-lifecycle-case {
                type workflow-case;
                description "The Service Lifecycle case (success,fail) for which to run the workflow.";
            }
            leaf workflow-id {
                type string;
                description "The ID of the workflow in Workflow Manager which needs to be executed.";
            }
            leaf blocking {
                type boolean;
                description "Describes if the workflow is blocking and must wait for the workflow to finish or timeout before moving on. Defaults to false.";
                default "false";
            }
            leaf execution-timeout {
                when "../blocking='true'";
                type int32;
                description "Describes the max timeout in sec, within which workflow is expected to finish. Defaults to 60. Applicable when workflow is blocking. If the timeout is exceeded the workflow will continue to run in the background.";
                default 60;
            }
        }
    }

    grouping template-report-info {
        leaf total {
            type int64;
        }
        leaf aligned {
            type int64;
        }
        leaf misaligned {
            type int64;
        }
        leaf oper-state-down {
            type int64;
        }
        list lifecycle-counts {
            leaf saved {
               type int64;
            }
            leaf planned {
                type int64;
            }
            leaf deployed {
                type int64;
            }
            leaf deployed-modified {
                type int64;
            }
            leaf removed {
                type int64;
            }
            leaf deleted {
                type int64;
            }
            leaf open {
                type int64;
            }
            leaf planned-failed {
               type int64;
            }
            leaf deployed-modified-failed {
                type int64;
            }
            leaf brownfield {
                type int64;
            }
            leaf pull-from-network-saved {
                type int64;
            }
            leaf pull-from-network-failed {
                type int64;
            }
            leaf composite-managed {
                type int64;
            }
            leaf unknown {
                type int64;
            }
        }
    }
}
