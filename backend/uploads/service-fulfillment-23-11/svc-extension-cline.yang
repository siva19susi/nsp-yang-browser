module svc-extension-cline {
    yang-version 1.1;
    namespace "urn:nokia:nsp:model:nsp-service:services:service-layer:svc-extension:cline";
    prefix "svc-extension-cline";
    import nsp-model-extensions { prefix model-ext; }
    import service-extension-common { prefix "svc-common"; }
    organization "Nokia";
    contact
        "Nokia NSP Support
         Web: <http://www.nokia.com>";
    description "Adds cline service Augmentation";
    revision "2023-06-27" { description "Move to extension common"; }
    revision "2022-10-26" { description "Endpoint tenant-id"; }
    revision "2022-04-19" { description "Add composite service association"; }
    revision "2021-11-30" { description "Add site-id to extension endpoint"; }
    revision "2021-04-14" { description "extension of the cline service-dmodel"; }

    typedef cpipe-vc-type {
        type enumeration {
            enum satope1   { value 12; }
            enum satopt1   { value 13; }
            enum satope3   { value 14; }
            enum satopt3   { value 15; }
            enum cesopsn    { value 16; }
            enum cesopsncas    { value 17; }
            enum satopserial   { value 19; }
            enum satoptpif { value 20; }
        }
        description "Specifies the cpipe site vc-type.";
    }


    grouping cline-svc {
        container cline-svc {
            model-ext:table-name "service-extension-cline-svc";

            leaf vc-type {
                type cpipe-vc-type;
                default satope1;
                description "The vc-type for cline services.";
            } //vc-type

            uses svc-common:svc-extension-common;
        }
    }


    grouping cline-site {
        container cline-site {
            model-ext:table-name "service-extension-cline-site";
            uses svc-common:site-extension;
        }
    }

    grouping cline-endpoint {
        container cline-endpoint {
            model-ext:table-name "service-extension-cline-endpoint";
            uses svc-common:endpoint-extension;
            leaf time-slots {
                type string;
                description "Time-slots information.";
            }
            uses cem-configuration-details;
        } //container
    } //augment cline endpoint

    grouping cem-configuration-details {
        container cem {
            description "Enter the cem context.";

           leaf rtp-header {
               type boolean;
               default "false";
               description
                   "Status whether RTP header to be used when packets are transmitted to the Packet Service Network.";
           }
           leaf payload-size {
               type uint32 {
                  range "0..2048";
               }
               units "bytes";
               description
               "The payload size (in bytes) of packets transmitted to the Packet Service Network (PSN) by the CEM SAP.";
           }

           leaf jitter-buffer {
               type uint32 {
                  range "1..250";
               }
               units "milliseconds";
               description "The jitter buffer size in milliseconds (ms).";
           }
       } // container cem
    }
}
