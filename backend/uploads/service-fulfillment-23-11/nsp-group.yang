module nsp-group {
    yang-version 1.1;
    namespace "urn:nokia:nsp:model:nsp-group";
    prefix group;


    import nsp-core {
        prefix core;
    }
    
    import nsp-useraccesscontrol {
        prefix useraccesscontrol;
    }
    
    import ietf-yang-types {
        prefix yang;
    }
    

    import nsp-model-extensions {
        prefix model-ext;
    }

    organization "Nokia";
    
    contact 
        "Nokia NSP Support
         Web: <http://www.nokia.com>";
    
    description 
        "YANG NBI definition for nsp-group model.";


       revision 2020-01-28 {
           description "Initial revision";
       }

    container filter {
        config true;
        list group-filter {
            key "name";
            config true;
    
            uses group-filter;
        }
    }

    container supervision {
        config true;
        container group {
            config true;
            list network {
                key "name";
                config true;
    
                uses network-supervision-group;
            }
            list service {
                key "name";
                config true;
    
                uses service-supervision-group;
            }
        }
        container view {
            config true;
            list network {
                key "name";
                config true;
    
                uses network-supervision-view;
            }
            list service {
                key "name";
                config true;
    
                uses service-supervision-view;
            }
        }
    }

    container resource {
        config true;
        container group {
            config true;
            list analytics {
                key "name";
                config true;
    
                uses analytics-resource-group;
            }
            list equipment {
                key "name";
                config true;
    
                uses equipment-group;
            }
            list lag {
                key "name";
                config true;
    
                uses lag-group;
            }
            list network-element {
                key "name";
                config true;
    
                uses network-element-group;
            }
            list service {
                key "name";
                config true;
    
                uses service-group;
            }
        }
        container group-directory {
            config true;
            list analytics {
                key "name";
                config true;
    
                uses analytics-resource-view;
            }
            list equipment {
                key "name";
                config true;
    
                uses equipment-view;
            }
            list lag {
                key "name";
                config true;
    
                uses lag-directory;
            }
            list network-element {
                key "name";
                config true;
    
                uses network-element-view;
            }
            list service {
                key "name";
                config true;
    
                uses service-view;
            }
        }
    }

    container mapLayout {
        config true;
        container layout {
            config true;
            list igp {
                key "name";
                config true;
    
                uses igp-map-layout;
            }
            list physical {
                key "name";
                config true;
    
                uses physical-map-layout;
            }
        }
        container region {
            config true;
            list igp {
                key "name";
                config true;
    
                uses igp-map-region;
            }
            list physical {
                key "name";
                config true;
    
                uses physical-map-region;
            }
        }
    }

    
    //
    // Entity: group-filter
    //
    grouping group-filter {
    
        uses group-filter-def;
    }
    
    grouping group-filter-def {
        description "Properties specific to 'group-filter'";
        
        leaf name {
             description "Name given to the filter by the user. The filterName may be unique within the source system.";
             type string;
        }
        
        leaf description {
             description "Description for the filter";
             type string;
        }
        
        leaf scope {
             description "Scope for the filter";
             type group:scope-type;
        }
        
        leaf span {
             description "Span for the filter. Indicates whether span of control is applied to the filter";
             type group:span-type;
        }
        
        leaf user-name {
             description "Applicable to private filter only, indicates userName of user who can view/use filter ";
             type string;
        }
        
        leaf filter-class-name {
             description "Name of the class to which this filter applies. The name should be full name, in format modelName.className";
             type string;
        }
        
        leaf expression {
             description "JSON string representing filter's expression";
             type string;
        }
        
        leaf creation-time {
             description "The time of creation of the object.";
             type yang:date-and-time;
        }
        
        leaf last-modified-time {
             description "The time of last modification of the object.";
             type yang:date-and-time;
        }
        
    }
    
    
    //
    // Entity: group
    //
    grouping group {
    
        uses group-def;
    }
    
    grouping group-def {
        description "Properties specific to 'group'";
        
        leaf name {
             description "Name given to the group by the user. The filterName may be unique within the source system.";
             type string;
        }
        
        leaf description {
             description "Description for the group";
             type string;
        }
        
        leaf app-category {
             description "Describes the purpose for which the group is created";
             type string;
        }
        
        leaf creation-time {
             description "The time of creation of the object.";
             type yang:date-and-time;
        }
        
        leaf last-modified-time {
             description "The time of last modification of the object.";
             type yang:date-and-time;
        }
        
        leaf-list access-rights {
            type instance-identifier {
                require-instance false;
            }
        }
        
        choice filter-member-choice {
            case filter-case {
                leaf-list filter {
                    type leafref {
                        require-instance false;
                        path "/group:filter/group:group-filter/group:name";
                    }
                }
                
            }
            case member-case {
                leaf-list member {
                    max-elements 2000000;
                    type instance-identifier {
                        require-instance false;
                    }
                }
                
            }
        }
    }
    
    
    //
    // Entity: supervision-group
    //
    grouping supervision-group {
    
        uses group-def;
        uses generic-group-def;
        uses supervision-group-def;
    }
    
    grouping supervision-group-def {
        description "Properties specific to 'supervision-group'";
        
        leaf auto-creation-method {
              config false;
             type string;
        }
        
        leaf alarm-severities {
             type group:alarms-severities;
        }
        
        leaf filter-editable {
             type boolean;
             default "true";
        }
        
        leaf layout-mode {
             type group:layout-mode;
        }
        
    }
    
    
    //
    // Entity: network-supervision-group
    //
    grouping network-supervision-group {
    
        uses group-def;
        uses generic-group-def;
        uses supervision-group-def;
        uses network-supervision-group-def;
    }
    
    grouping network-supervision-group-def {
        description "Properties specific to 'network-supervision-group'";
        
    }
    
    
    //
    // Entity: service-supervision-group
    //
    grouping service-supervision-group {
    
        uses group-def;
        uses generic-group-def;
        uses supervision-group-def;
        uses service-supervision-group-def;
    }
    
    grouping service-supervision-group-def {
        description "Properties specific to 'service-supervision-group'";
        
    }
    
    
    //
    // Entity: generic-group
    //
    grouping generic-group {
    
        uses group-def;
        uses generic-group-def;
    }
    
    grouping generic-group-def {
        description "Properties specific to 'generic-group'";
        
        leaf creation-type {
             type group:creation-type;
        }
        
        leaf creation-details {
             type string;
        }
        
    }
    
    
    //
    // Entity: network-element-group
    //
    grouping network-element-group {
    
        uses group-def;
        uses generic-group-def;
        uses network-element-group-def;
    }
    
    grouping network-element-group-def {
        description "Properties specific to 'network-element-group'";
        
    }
    
    
    //
    // Entity: equipment-group
    //
    grouping equipment-group {
    
        uses group-def;
        uses generic-group-def;
        uses equipment-group-def;
    }
    
    grouping equipment-group-def {
        description "Properties specific to 'equipment-group'";
        
    }
    
    
    //
    // Entity: service-group
    //
    grouping service-group {
    
        uses group-def;
        uses generic-group-def;
        uses service-group-def;
    }
    
    grouping service-group-def {
        description "Properties specific to 'service-group'";
        
    }
    
    
    //
    // Entity: analytics-resource-group
    //
    grouping analytics-resource-group {
    
        uses group-def;
        uses generic-group-def;
        uses analytics-resource-group-def;
    }
    
    grouping analytics-resource-group-def {
        description "Properties specific to 'analytics-resource-group'";
        
    }
    
    
    //
    // Entity: lag-group
    //
    grouping lag-group {
    
        uses group-def;
        uses generic-group-def;
        uses lag-group-def;
    }
    
    grouping lag-group-def {
        description "Properties specific to 'lag-group'";
        
    }
    
    
    //
    // Entity: summary-view
    //
    grouping summary-view {
    
        uses group-def;
        uses summary-view-def;
    }
    
    grouping summary-view-def {
        description "Properties specific to 'summary-view'";
        
        leaf creation-type {
              config false;
             type group:creation-type;
        }
        
    }
    
    
    //
    // Entity: network-supervision-view
    //
    grouping network-supervision-view {
    
        uses group-def;
        uses summary-view-def;
        uses network-supervision-view-def;
    }
    
    grouping network-supervision-view-def {
        description "Properties specific to 'network-supervision-view'";
        
    }
    
    
    //
    // Entity: service-supervision-view
    //
    grouping service-supervision-view {
    
        uses group-def;
        uses summary-view-def;
        uses service-supervision-view-def;
    }
    
    grouping service-supervision-view-def {
        description "Properties specific to 'service-supervision-view'";
        
    }
    
    
    //
    // Entity: network-element-view
    //
    grouping network-element-view {
    
        uses group-def;
        uses summary-view-def;
        uses network-element-view-def;
    }
    
    grouping network-element-view-def {
        description "Properties specific to 'network-element-view'";
        
    }
    
    
    //
    // Entity: equipment-view
    //
    grouping equipment-view {
    
        uses group-def;
        uses summary-view-def;
        uses equipment-view-def;
    }
    
    grouping equipment-view-def {
        description "Properties specific to 'equipment-view'";
        
    }
    
    
    //
    // Entity: service-view
    //
    grouping service-view {
    
        uses group-def;
        uses summary-view-def;
        uses service-view-def;
    }
    
    grouping service-view-def {
        description "Properties specific to 'service-view'";
        
    }
    
    
    //
    // Entity: analytics-resource-view
    //
    grouping analytics-resource-view {
    
        uses group-def;
        uses summary-view-def;
        uses analytics-resource-view-def;
    }
    
    grouping analytics-resource-view-def {
        description "Properties specific to 'analytics-resource-view'";
        
    }
    
    
    //
    // Entity: lag-directory
    //
    grouping lag-directory {
    
        uses group-def;
        uses summary-view-def;
        uses lag-directory-def;
    }
    
    grouping lag-directory-def {
        description "Properties specific to 'lag-directory'";
        
    }
    
    
    //
    // Entity: map-layout
    //
    grouping map-layout {
    
        uses group-def;
        uses summary-view-def;
        uses map-layout-def;
    }
    
    grouping map-layout-def {
        description "Properties specific to 'map-layout'";
        
        leaf coordinate-system {
             description "The coordinate system used in the map layout";
             type group:coordinate-system;
             default "cartesian";
        }
        
    }
    
    
    //
    // Entity: physical-map-layout
    //
    grouping physical-map-layout {
    
        uses group-def;
        uses summary-view-def;
        uses map-layout-def;
        uses physical-map-layout-def;
    }
    
    grouping physical-map-layout-def {
        description "Properties specific to 'physical-map-layout'";
        
    }
    
    
    //
    // Entity: igp-map-layout
    //
    grouping igp-map-layout {
    
        uses group-def;
        uses summary-view-def;
        uses map-layout-def;
        uses igp-map-layout-def;
    }
    
    grouping igp-map-layout-def {
        description "Properties specific to 'igp-map-layout'";
        
        container origin-group {
            description "";
            uses group;
        
        }
        
    }
    
    
    //
    // Entity: map-region
    //
    grouping map-region {
    
        uses group-def;
        uses generic-group-def;
        uses supervision-group-def;
        uses map-region-def;
    }
    
    grouping map-region-def {
        description "Properties specific to 'map-region'";
        
    }
    
    
    //
    // Entity: physical-map-region
    //
    grouping physical-map-region {
    
        uses group-def;
        uses generic-group-def;
        uses supervision-group-def;
        uses map-region-def;
        uses physical-map-region-def;
    }
    
    grouping physical-map-region-def {
        description "Properties specific to 'physical-map-region'";
        
    }
    
    
    //
    // Entity: igp-map-region
    //
    grouping igp-map-region {
    
        uses group-def;
        uses generic-group-def;
        uses supervision-group-def;
        uses map-region-def;
        uses igp-map-region-def;
    }
    
    grouping igp-map-region-def {
        description "Properties specific to 'igp-map-region'";
        
        container origin-group {
            description "";
            uses group;
        
        }
        
    }
    
    
    //
    // Entity: map-zone
    //
    grouping map-zone {
    
        uses map-zone-def;
    }
    
    grouping map-zone-def {
        description "Properties specific to 'map-zone'";
        
        leaf name {
             description "zone name";
             type string;
        }
        
        leaf app-category {
             description "zone category";
             type string;
        }
        
        leaf origin {
             description "optional origin zone fdn";
             type instance-identifier {
                require-instance false;
            }
        }
        
        leaf target {
             description "optional target zone fdn";
             type instance-identifier {
                require-instance false;
            }
        }
        
    }
    
    
    //
    // Entity: implicit-relation
    //
    grouping implicit-relation {
    
        uses implicit-relation-def;
    }
    
    grouping implicit-relation-def {
        description "Properties specific to 'implicit-relation'";
        
        leaf original-member {
             type instance-identifier {
                require-instance false;
            }
        }
        
        leaf implied-member {
             type instance-identifier {
                require-instance false;
            }
        }
        
    }
    
    
    
    
    //
    // Enumeration: scope-type
    //
    typedef scope-type {
    
        type enumeration {
            enum private {
                value 0;
            }
    
            enum public {
                value 1;
            }
    
        }
    }
    
    //
    // Enumeration: span-type
    //
    typedef span-type {
    
        type enumeration {
            enum off {
                value 0;
            }
    
            enum user {
                value 1;
            }
    
        }
    }
    
    //
    // Enumeration: creation-type
    //
    typedef creation-type {
    
        type enumeration {
            enum nfm-import {
                value 0;
            }
    
            enum auto {
                value 1;
            }
    
            enum manual {
                value 2;
            }
    
            enum nfmp-topology-import {
                value 3;
            }
    
            enum generic-ne {
                value 4;
            }
    
            enum generic-service {
                value 5;
            }
    
            enum generic-equipment {
                value 6;
            }
    
            enum map-layout-import {
                value 7;
            }
    
            enum implicit {
                value 8;
            }
    
        }
    }
    
    //
    // Enumeration: alarms-severities
    //
    typedef alarms-severities {
    
        type enumeration {
            enum critical {
                value 1;
            }
    
            enum critical-major {
                value 2;
            }
    
            enum critical-major-minor {
                value 3;
            }
    
            enum all {
                value 4;
            }
    
        }
    }
    
    //
    // Enumeration: upgrade-status
    //
    typedef upgrade-status {
    
        type enumeration {
            enum failed {
                value 0;
            }
    
            enum succeed-and-not-cleaned {
                value 1;
            }
    
            enum succeed-and-cleaned {
                value 2;
            }
    
        }
    }
    
    //
    // Enumeration: layout-mode
    //
    typedef layout-mode {
    
        type enumeration {
            enum none {
                value 0;
            }
    
            enum nfmp {
                value 1;
            }
    
            enum region {
                value 2;
            }
    
        }
    }
    
    //
    // Enumeration: action-type
    //
    typedef action-type {
    
        type enumeration {
            enum unknown {
                value 0;
            }
    
            enum create {
                value 1;
            }
    
            enum delete {
                value 2;
            }
    
            enum update {
                value 3;
            }
    
            enum implicit-update {
                value 4;
            }
    
        }
    }
    
    //
    // Enumeration: coordinate-system
    //
    typedef coordinate-system {
        description "Types of coordinate system that specifies the position of a member";
    
        type enumeration {
            enum cartesian {
                value 0;
            }
    
            enum geographic {
                value 1;
            }
    
        }
    }
    
    
    
}
