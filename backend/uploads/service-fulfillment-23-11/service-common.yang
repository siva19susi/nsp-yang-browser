module service-common {
    yang-version 1.1;
    namespace "urn:nokia:nsp:service-common";
    prefix "service-common";
    import nsp-common {prefix common;}
    import nsp-model-extensions { prefix model-ext; }
    organization "Nokia";
    contact
            "Nokia NSP Support
             Web: <http://www.nokia.com>";
    description "YANG definition nsp-service related operations";

    revision "2023-01-20" { description  "add service-type enum"; }

    typedef service-type {
        type enumeration {
            enum unknown;
            enum eline;
            enum elan;
            enum l3vpn;
            enum mpr-backhaul;
            enum ies;
            enum cline;
            enum apipe;
            enum ipipe;
            enum fpipe;
            enum hpipe;
        }
        description "Specify the service type.";
    }
}
