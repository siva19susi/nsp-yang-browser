module nsp-service-associate {

    yang-version 1.1;
    namespace "urn:nokia:nsp:model:nsp-service-associate";
    prefix "nsp-service-associate";
    import nsp-model-extensions { prefix "model-ext"; }
    revision "2022-12-15" { description "Initial revision.";}
    
    grouping un-associate-service-response {
        list invalid-services {
            leaf service-id {
                type string;
            }
            leaf error-msg {
                type string;
            }
        }  
    }

    rpc unassociate {
        description
            "Dis-associate given services from associated template";
        model-ext:operation java {
            model-ext:class com.nokia.nsp.sf.app.unassociate.operations.ServiceAssociateOperationExecutor;
        }

        input {
            leaf-list service-ids {
                type string;
                min-elements 1;
                max-elements 200;
                description
                    "List of services to be un-associated.";
            }
        }
        output {
            uses un-associate-service-response;
        }
    }
}
