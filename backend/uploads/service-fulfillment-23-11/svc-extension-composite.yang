module svc-extension-composite {
    yang-version 1.1;
    namespace "urn:nokia:nsp:model:nsp-service:services:service-layer:svc-extension:composite";
    prefix "svc-extension-composite";
    import nsp-model-extensions { prefix model-ext; }
    import service-extension-common { prefix "svc-common"; }
    import service-extension-common-types { prefix "svc-common-types"; }
    import service-template { prefix "svc-template"; }
    organization "Nokia";
    contact
        "Nokia NSP Support
        Web: <http://www.nokia.com>";
    description "Adds composite service Augmentation";
    revision "2023-07-22" { description "Move to extension common"; }
    revision "2022-03-28" { description "extension of the composite service model"; }


    grouping composite-svc {
        container composite-svc {
            model-ext:table-name "svc-extension-composite";
            leaf slc-state {
                type svc-common-types:olc;
                default deployed;
                description "The service life cycle state.";
            }

            leaf job-id {
                type string;
                description "The work-order number.";
            }
            leaf intent-type {
                type string;
                description "The intent-type.";
            }
            leaf intent-type-version {
                type string;
                description "Specify intent type version.";
            }
            leaf  intent-instance-identifier {
                type string;
                description "The intent-instance-identifier of the service.";
            }

            leaf template-name { //TODO - unique and require-instance=true
                type leafref {
                    require-instance false;
                    path "/svc-template:templates/svc-template:template/svc-template:name";
                }
                description "The template-name of the service";
            }
            leaf misaligned {
                type boolean;
                description "Specifies if the service is misaligned with the network";
                default false;
            }
            uses svc-common:slc-details;
            uses svc-common:deployer-details;
            uses svc-common:job-details;
        }
    }

}
