module nsp-service-actions {
    yang-version "1.1";
    namespace "urn:nokia:nsp:nsp-service-actions";
    prefix "nsp-service-actions";
    import nsp-common {prefix common;}
    import nsp-model-extensions { prefix model-ext; }
    import service-common {prefix service-common; }
    organization "Nokia";
    contact
            "Nokia NSP Support
             Web: <http://www.nokia.com>";
    description "YANG definition nsp-service related actions";

    revision "2023-04-14" { description  "add RPC definitions for calculate-oper-state"; }

    rpc calculate-oper-state{
        description "This rpc use to calculate oper state";
        input {
            leaf service-type {
                type service-common:service-type;
                description "Specify the service type to resync";
            }
            leaf service-id {
                type string;
                description "Specify the service-id to resync";
            }
        }
    }

    rpc resync-services{
        description "This rpc usage is to sync the services from network.";
        input {
            leaf service-type {
                type service-common:service-type;
                description "Specify the service type to resync";
            }
            leaf service-id {
                type string;
                description "Specify the service-id to resync";
            }
        }
    }

}
