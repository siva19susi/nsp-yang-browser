module ietf-datastores {

    yang-version 1.1;

    namespace
      "urn:ietf:params:xml:ns:yang:ietf-datastores";

    prefix ds;

    organization
      "IETF Network Modeling (NETMOD) Working Group";

    contact
      "WG Web:   <https://datatracker.ietf.org/wg/netmod/>

     WG List:  <mailto:netmod@ietf.org>

     Author:   Martin Bjorklund
               <mailto:mbj@tail-f.com>

     Author:   Juergen Schoenwaelder
               <mailto:j.schoenwaelder@jacobs-university.de>

     Author:   Phil Shafer
               <mailto:phil@juniper.net>

     Author:   Kent Watsen
               <mailto:kwatsen@juniper.net>

     Author:   Rob Wilton
               <rwilton@cisco.com>";

    description
      "This YANG module defines two sets of identities for datastores.
     The first identifies the datastores themselves, the second
     identifies datastore properties.

     Copyright (c) 2017 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
     (http://trustee.ietf.org/license-info).

     This version of this YANG module is part of RFC XXXX
     (http://www.rfc-editor.org/info/rfcxxxx); see the RFC itself
     for full legal notices.";

    revision "2017-08-17" {
      description "Initial revision.";
      reference
        "RFC XXXX: Network Management Datastore Architecture";

    }


    identity datastore {
      description
        "Abstract base identity for datastore identities.";
    }

    identity conventional {
      base datastore;
      description
        "Abstract base identity for conventional configuration
       datastores.";
    }

    identity running {
      base conventional;
      description
        "The running configuration datastore.";
    }

    identity candidate {
      base conventional;
      description
        "The candidate configuration datastore.";
    }

    identity startup {
      base conventional;
      description
        "The startup configuration datastore.";
    }

    identity intended {
      base conventional;
      description
        "The intended configuration datastore.";
    }

    identity dynamic {
      base datastore;
      description
        "Abstract base identity for dynamic configuration datastores.";
    }

    identity operational {
      base datastore;
      description
        "The operational state datastore.";
    }

    typedef datastore-ref {
      type identityref {
        base datastore;
      }
      description
        "A datastore identity reference.";
    }
  }  // module ietf-datastores
