module nsp-service-intent {
    yang-version 1.1;
    namespace "urn:nokia:nsp:model:nsp-service-intent";
    prefix "nsp-service-intent";
    import service-extension-common-types { prefix "svc-common-types"; }
    import nsp-intent-common-types { prefix "nsp-intent-common-types"; }
    organization "NOKIA Corp";
    contact "";
    description "";

    revision "2023-09-25" { description "Add deployment-state and deployment-tracking-id to intent-base"; }
    revision "2023-06-27" { description "Move to extension common"; }
    revision "2023-03-22" {
        description
            "23.4 change - set service-ids max-elements";
    }

    revision "2022-09-28" {
        description
                "23.4 change - remove schemaMount";
    }

    revision "2020-10-19" {
        description
                "Initial revision.";
    }

    container intent-base {

        list intent {
            key "service-name intent-type";

            leaf intent-type {
                 type string;
                 description "The intent type.";
            }

            leaf service-name {
                type string;
                description "The the name of service.";
            }

            leaf intent-type-version {
                  type string;
                  description "The intent type version.";
            }

            leaf olc-state {
                type svc-common-types:olc;
                default "saved";
                description "The desired object life cycle state.";
            }

            leaf template-name {
                type string;
                description "The template name.";
            }

            leaf deployment-state {
            type nsp-intent-common-types:deployer-state-type;
                default notstarted;
                config false;
                description "overall deployment state";
            }

            leaf deployment-tracking-id {
                type string;
                config false;
                description "deployment tracking xpath, contains info on submitted jobs from intents.";
            }

        }

   }

    rpc audit {
        input {
            leaf intent-type {
                type string;
                description "The intent type.";
            }

            leaf service-name {
                type string;
                description "The service name.";
            }
        }
     }

    rpc synchronize {
        input {
            leaf intent-type {
                type string;
                description "The intent type.";
            }

            leaf service-name {
                type string;
                description "The service name.";
            }
        }
     }

     rpc change-olc-state {
         input {
             leaf intent-type {
                 type string;
                 description "The intent type.";
             }

             leaf service-name {
                 type string;
                 description "The service name.";
             }

             leaf target-state {
                 type svc-common-types:olc;
                 description "The desired olc state.";
             }

             leaf ignore-blocking-workflow {
                 type boolean;
                 description "Ignore blocking workflow with a failed execution state.";
             }
         }
     }

    rpc rerun-blocking-workflow {
        input {
            leaf intent-type {
                type string;
                description "The intent type.";
            }

            leaf service-name {
                type string;
                description "The service name.";
            }
        }
    }

    rpc create-intent-from-services {
        input {
            leaf template-name {
                type string;
                description "The name of the template to associated to.";
            }

            leaf-list service-ids {
                type string;
                min-elements 1;
                max-elements 200;
                description "A list of service id.";
            }

            leaf max-site-per-request {
                type int8;
                description "Use this for serivces with large number of sites to limit site model mapping";
            }
        }
    }
}
