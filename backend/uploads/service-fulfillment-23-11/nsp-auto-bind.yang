module nsp-auto-bind {
    yang-version "1.1";
    namespace "urn:nokia:nsp:model:nsp-auto-bind";
    prefix "nsp-auto-bind";

    import nokia-extensions {
        prefix "nokia-ext";
    }

    import nsp-model-extensions {
        prefix "model-ext";
    }

    import ietf-yang-types {
        prefix "yang";
    }

    description ""; //todo

    revision "2023-08-01" {
        description "Initial revision.";
    }

    nokia-ext:model-version "1.0.0";

    grouping service-site {
        description
            "Combination of NE IP address and service ID to uniquely identify a source of collection.";

        leaf service-id {
            description
                "ID which uniquely identifies a service on the router.";
            type string;
        }
        leaf site {
            description
                "NE ID of router as marked by Device Administrator.";
            type string;
        }
        leaf service-type {
            description
                "The type of service. Allowed values are: vprn, evpn-epipe, evpn-vpls.";
            type string;
        }
        leaf last-resynced-time {
            description
                "Timestamp for the last time this data was retrieved from the node.";
            type yang:date-and-time;
        }
    }

    grouping bound-tunnel {
        description
            "Grouping of paramters that define a single bound tunnel for transportations";

        leaf tunnel-name {
            description
                "Name of the tunnel. Currently only supported for RSVP and SR-TE LSPs.";
            type string;
        }
        leaf tunnel-type {
            description
                "Protocol being used for tunneling.";
            type string;
        }
        leaf tunnel-id {
            description
                "ID of the tunnel being used.";
            type uint32;
        }
        leaf far-end {
            description
                "IP address of the far-end of the tunnel.";
            type string;
        }
        leaf binding-timestamp {
            description
                "A timestamp of the moment the tunnel in question was bound.
                Converted from the age displayed in the service route table.";
            type yang:date-and-time;
        }
    }

    container auto-bind-service {
        list auto-bind-tunnels {
            model-ext:table-name "nsp_auto_bind_services";
            key "site service-id";
            uses service-site-tunnels;
        }
        action read-tunnels {
            description "Read auto-bind tunnels from node";
            input {
                leaf site {
                    type string;
                }
                leaf service-id {
                    type string;
                }
                leaf service-type {
                    type string;
                }
            }
            output {
                list auto-bind-tunnels {
                    key "site service-id";
                    uses service-site-tunnels;
                }
            }
        }
        action find-services {
            description "Reverse lookup of service-ids from tunnel-id and site";
            input {
                leaf site {
                    type string;
                }
                leaf tunnel-id {
                    type uint32;
                }
            }
            output {
                leaf-list service-ids {
                    type string;
                }
            }
        }
        action reload-config {
            description "Reload configuration";
            // TODO figure out a map data structure for output
        }
    }

    grouping service-site-tunnels {
        description
            "Grouping listing all bound tunnels for a single service site.";

        uses service-site;

        list bound-tunnels {
            model-ext:table-name "nsp_auto_bind_tunnels";
            key tunnel-name;
            uses bound-tunnel;
        }
    }
}
