module svc-extension-ipipe {
    yang-version 1.1;
    namespace "urn:nokia:nsp:model:nsp-service:services:service-layer:svc-extension:ipipe";
    prefix "svc-extension-ipipe";
    import nsp-model-extensions { prefix model-ext; }
    import service-extension-common { prefix "svc-common"; }
    organization "Nokia";
    contact
        "Nokia NSP Support
         Web: <http://www.nokia.com>";
    description "Adds ipipe service Augmentation";
    revision "2023-06-27" { description "Move to extension common"; }
    revision "2022-10-26" { description "Endpoint tenant-id"; }
    revision "2022-10-13" { description "Initial setup"; }

    grouping ipipe-svc {
        container ipipe-svc {
            model-ext:table-name "service-extension-ipipe-svc";
            uses svc-common:svc-extension-common;
        }
    }

    grouping ipipe-site {
        container ipipe-site {
            model-ext:table-name "service-extension-ipipe-site";
            uses svc-common:site-extension;
        }
    }

    grouping ipipe-endpoint {
        container ipipe-endpoint {
            model-ext:table-name "service-extension-ipipe-endpoint";
            uses svc-common:endpoint-extension;
        } //container
    } //augment ipipe endpoint

}
