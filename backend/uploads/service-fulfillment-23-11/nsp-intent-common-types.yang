module nsp-intent-common-types {
    yang-version 1.1;
    namespace "urn:nokia:nsp:nsp-intent-common-types";
    prefix "nsp-intent-common-types";
    organization "Nokia";
    contact
            "Nokia NSP Support
             Web: <http://www.nokia.com>";
    description "YANG definition nsp-intent-common-types";

    revision "2023-09-25" { description  "add deployer-state-type enum"; }

    typedef deployer-state-type {
        type enumeration {
            enum running {
                value 0;
                description "The deployer is in progress";
            }
            enum success {
                value 1;
                description "The deployer succeeded";
            }
            enum failed {
                value 2;
                description "The deployer failed";
            }
            enum notstarted {
                value 3;
                description "The deployer not started";
            }
        }
        description "state of the deployer";
    }
}
