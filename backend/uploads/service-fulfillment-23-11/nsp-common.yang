module nsp-common {
    yang-version 1.1;
    namespace "urn:nokia:nsp:model:nsp-common";
    prefix common;



    import nsp-model-extensions {
        prefix model-ext;
    }

    organization "Nokia";
    
    contact 
        "Nokia NSP Support
         Web: <http://www.nokia.com>";
    
    description 
        "YANG NBI definition for nsp-common model.";


    revision 2019-06-28 {
        description "Initial revision";
    }

    
    
    
    //
    // Enumeration: oper-state
    //
    typedef oper-state {
        description "The operational state.
             If a piece of equipment does not have an operational state,
             then that component's operational state can be mapped to:
             present = operationally up,
             absent = operationally down.
             Refer to X.731 standard for more information (https://www.itu.int/rec/T-REC-X.731-199201-I/en)";
    
        type enumeration {
            enum unknown {
                value 0;
            }
    
            enum enabled {
                value 1;
                description "The resource is operable and available for use";
            }
    
            enum disabled {
                value 2;
                description "The resource is totally inoperable and unable to provide services";
            }
    
        }
    }
    
    //
    // Enumeration: admin-state
    //
    typedef admin-state {
        description "The administrative state.
             Only equipment with adminState Unlocked will be included in KPI calculation.
             Refer to X.731 standard for more information (https://www.itu.int/rec/T-REC-X.731-199201-I/en)";
    
        type enumeration {
            enum unknown {
                value 0;
            }
    
            enum unlocked {
                value 1;
                description "The resource is administratively permitted to perform services. In other words, the resource is 'up'.";
            }
    
            enum locked {
                value 2;
                description "The resource is administratively prohibited from performing services. In other words, the resource is 'down'";
            }
    
            enum forced-lockout {
                value 3;
                description "Use of resource is administratively prohibited from performing services and any existing services are moved off to different resources.";
            }
    
            enum shutting-down {
                value 4;
                description "Use of resource is administratively permitted for existing usage only. In other words, existing usage remains unaffected.";
            }
    
            enum maintenance {
                value 5;
                description "The resource is under maintenance. Generally configuration is disallowed when in this state.";
            }
    
        }
    }
    
    //
    // Enumeration: standby-state
    //
    typedef standby-state {
        description "The standby state.
             Refer to X.731 standard for more information (https://www.itu.int/rec/T-REC-X.731-199201-I/en)";
    
        type enumeration {
            enum providing-service {
                value 1;
                description "The back-up resource is providing service and is backing up another resource.";
            }
    
            enum standby {
                value 2;
                description "The resource is not providing service, but is to back-up another resource.";
            }
    
        }
    }
    
    //
    // Enumeration: availability-state
    //
    typedef availability-state {
        description "The availability state.
             Refer to X.731 standard for more information (https://www.itu.int/rec/T-REC-X.731-199201-I/en)";
    
        type enumeration {
            enum unknown {
                value 0;
            }
    
            enum in-test {
                value 1;
                description "The resource is undergoing a test procedure. The operational state is enabled.";
            }
    
            enum failed {
                value 2;
                description "The resource has an internal fault that prevents it from operating. The operational state is disabled.";
            }
    
            enum degraded {
                value 3;
                description "The service available from the resource is degraded in some respect; the resource is partially down or suspended. The operational state is enabled.";
            }
    
            enum off-line {
                value 4;
                description "The resource requires a routine operation to be performed to place it online and make it available for use. The operational state is disabled.";
            }
    
            enum power-off {
                value 5;
                description "The resource requires power to be applied and is not powered on. The operational state is disabled.";
            }
    
            enum off-duty {
                value 6;
                description "The resource has been made inactive. The operational state is enabled or disabled.";
            }
    
            enum dependency {
                value 7;
                description "The resource cannot operate because some other resource on which it depends is unavailable. The operational state is disabled.";
            }
    
            enum not-installed {
                value 8;
                description "The resource represented by the managed object is not present, or is incomplete. The operational state is disabled.";
            }
    
            enum log-full {
                value 9;
                description "This indicates a log full condition";
            }
    
        }
    }
    
    //
    // Enumeration: source-type
    //
    typedef source-type {
        description "Used to identify the type of the source system of the managed object";
    
        type enumeration {
            enum other {
                value 0;
            }
    
            enum nsd {
                value 1;
            }
    
            enum nfmp {
                value 2;
            }
    
            enum nfmt {
                value 3;
            }
    
            enum nrcp {
                value 4;
            }
    
            enum nrct {
                value 5;
            }
    
            enum nrcf {
                value 6;
            }
    
            enum nrcx {
                value 7;
            }
    
            enum mdm {
                value 8;
            }
    
            enum nsp {
                value 9;
            }
    
            enum tsc {
                value 10;
            }
    
        }
    }
    
    //
    // Enumeration: speed-units
    //
    typedef speed-units {
        description "Common units used for rates";
    
        type enumeration {
            enum unknown {
                value 0;
            }
    
            enum kbps {
                value 1;
                description "Kilobits per second";
            }
    
            enum mbps {
                value 2;
                description "Megabits per second";
            }
    
        }
    }
    
    //
    // Enumeration: time-units
    //
    typedef time-units {
        description "Common units used for time";
    
        type enumeration {
            enum unknown {
                value 0;
            }
    
            enum nanoseconds {
                value 1;
            }
    
            enum microseconds {
                value 2;
            }
    
            enum milliseconds {
                value 3;
            }
    
            enum seconds {
                value 4;
            }
    
            enum minutes {
                value 5;
            }
    
            enum hours {
                value 6;
            }
    
            enum days {
                value 7;
            }
    
        }
    }
    
    //
    // Enumeration: address-family
    //
    typedef address-family {
        description "Address family based off IANA-ADDRESS-FAMILY-NUMBERS-MIB.AddressFamilyNumbers";
    
        type enumeration {
            enum other {
                value 0;
            }
    
            enum ip-v4 {
                value 1;
            }
    
            enum ip-v6 {
                value 2;
            }
    
            enum nsap {
                value 3;
            }
    
            enum hdlc {
                value 4;
            }
    
            enum bbn1822 {
                value 5;
            }
    
            enum all802 {
                value 6;
            }
    
            enum e163 {
                value 7;
            }
    
            enum e164 {
                value 8;
            }
    
            enum f69 {
                value 9;
            }
    
            enum x121 {
                value 10;
            }
    
            enum ipx {
                value 11;
            }
    
            enum apple-talk {
                value 12;
            }
    
            enum decnet-iv {
                value 13;
            }
    
            enum banyan-vines {
                value 14;
            }
    
            enum e164with-nsap {
                value 15;
            }
    
            enum dns {
                value 16;
            }
    
            enum distinguished-name {
                value 17;
            }
    
            enum as-number {
                value 18;
            }
    
            enum xtp-over-ipv4 {
                value 19;
            }
    
            enum xtp-over-ipv6 {
                value 20;
            }
    
            enum xtp-native-mode-xtp {
                value 21;
            }
    
            enum fibre-channel-wwpn {
                value 22;
            }
    
            enum fibre-channel-wwnn {
                value 23;
            }
    
            enum gwid {
                value 24;
            }
    
            enum afi {
                value 25;
            }
    
            enum mpls-tp-section-endpoint-identifier {
                value 26;
            }
    
            enum mpls-tp-lsp-endpoint-identifier {
                value 27;
            }
    
            enum mpls-tp-pseudowire-endpoint-identifier {
                value 28;
            }
    
            enum eigrp-common-service-family {
                value 16384;
            }
    
            enum eigrp-ipv4-service-family {
                value 16385;
            }
    
            enum eigrp-ipv6-service-family {
                value 16386;
            }
    
            enum lisp-canonical-address-format {
                value 16387;
            }
    
            enum bgp-ls {
                value 16388;
            }
    
            enum fortyeight-bit-mac-bit-mac {
                value 16389;
            }
    
            enum sixtyfour-bit-mac {
                value 16390;
            }
    
            enum oui {
                value 16391;
            }
    
            enum mac24 {
                value 16392;
            }
    
            enum mac40 {
                value 16393;
            }
    
            enum ipv664 {
                value 16394;
            }
    
            enum rbridge-port-id {
                value 16395;
            }
    
            enum trill-nickname {
                value 16396;
            }
    
            enum reserved {
                value 65535;
            }
    
        }
    }
    
    
    
}
