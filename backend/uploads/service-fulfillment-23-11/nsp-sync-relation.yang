module nsp-sync-relation {
    yang-version 1.1;
    namespace "urn:nokia:nsp:model:nsp-sync-relation";
    prefix "nsp-sync-relation";
    import nsp-model-extensions { prefix model-ext; }
    organization "Nokia";
    contact
        "Nokia NSP Support
         Web: <http://www.nokia.com>";
    description "Adds Device Site configuration model";

    revision "2022-09-13" { description "nsp sync relation model inital version"; }

    model-ext:include-sources true;

    container sites {
        list device-site {
            key "site-id info-id";
            leaf site-id {
                description "The site identifier.";
                type string;
            }
            leaf info-id {
                description "The name of the policystatement";
                type string;
            }
            leaf-list info {
                type string {
                    length "0..10485760";
                }
                description "Specify a list of info cummunity";
            }
            description "Holding the device object relation";
            model-ext:notif-suppress true;
        }
        list tracking-device-site {
            key "site-id db-id";
            leaf site-id {
                description "The site identifier.";
                type string;
            }
            leaf db-id {
                description "The db-ids";
                type int64;
            }
            description "Holding the info during resync and figuring out delta";
            model-ext:notif-suppress true;
        }
    }
}
