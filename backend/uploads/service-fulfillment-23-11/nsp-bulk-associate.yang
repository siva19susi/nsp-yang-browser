module nsp-bulk-associate {

    yang-version 1.1;
    namespace "urn:nokia:nsp:model:nsp-bulk-associate";
    prefix "nsp-bulk-associate";

    import nsp-model-extensions { prefix "model-ext"; }

    revision "2022-11-15" { description "Initial revision.";}

    grouping not-associated-service-report {
        leaf non-associated {
            type int32;
            description
                "total number of services which are not associated with any template";
        }

        leaf valid-for-association {
            type int32;
            description
                "total number of services which are valid for association with a templated";
        }
    }

    grouping progress-report {
        leaf association-completed {
            type int32;
            description
                "total number of services which are successfully associate with a template";
        }

        leaf association-failed {
            type int32;
            description
                "total number of services which failed to associate with a template";
        }

        leaf association-pending {
            type int32;
            description
                "total number of services which are pending to be associated with a template";
        }
    }

    rpc execute {
        description
            "Start association of services which are eligible by bulk-association rules";
        model-ext:operation java {
            model-ext:class com.nokia.nsp.sf.app.bulkassociate.operations.BulkAssociateOperationExecutor;
        }
        output {
            leaf result {
                type string;
            }
        }
    }

   rpc stop {
        description
            "Stop association of services which are eligible by bulk-association rules";
        model-ext:operation java {
            model-ext:class com.nokia.nsp.sf.app.bulkassociate.operations.BulkAssociateOperationExecutor;
        }
        output {
            leaf result {
                type string;
            }
        }
    }

    rpc run-status {
        description
            "Start association of services which are eligible by bulk-association rules";
        model-ext:operation java {
            model-ext:class com.nokia.nsp.sf.app.bulkassociate.operations.BulkAssociateOperationExecutor;
        }
        output {
            leaf result {
                type boolean;
            }
        }
    }

    rpc pre-associate-report {
        description
            "a report of not associated services";
        model-ext:operation java {
            model-ext:class com.nokia.nsp.sf.app.bulkassociate.operations.BulkAssociateOperationExecutor;
        }
        output {
            uses not-associated-service-report;
        }
    }

    rpc progress-report {
        description
            "a report of last bulk-association status progress report";
        model-ext:operation java {
            model-ext:class com.nokia.nsp.sf.app.bulkassociate.operations.BulkAssociateOperationExecutor;
        }
        output {
            uses progress-report;
        }
    }
}
