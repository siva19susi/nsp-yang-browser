module svc-extension-fpipe {
    yang-version 1.1;
    namespace "urn:nokia:nsp:model:nsp-service:services:service-layer:svc-extension:fpipe";
    prefix "svc-extension-fpipe";
    import nsp-model-extensions { prefix model-ext; }
    import service-extension-common { prefix "svc-common"; }
    organization "Nokia";
    contact
        "Nokia NSP Support
         Web: <http://www.nokia.com>";
    description "Adds fpipe service Augmentation";
    revision "2023-06-27" { description "Move to extension common"; }
    revision "2022-10-26" { description "Endpoint tenant-id"; }
    revision "2022-10-13" { description "Initial setup"; }

    grouping fpipe-svc {
        container fpipe-svc {
            model-ext:table-name "service-extension-fpipe-svc";
            uses svc-common:svc-extension-common;
        }
    }

    grouping fpipe-site {
        container fpipe-site {
            model-ext:table-name "service-extension-fpipe-site";
            uses svc-common:site-extension;
        }
    }

    grouping fpipe-endpoint {
        container fpipe-endpoint {
            model-ext:table-name "service-extension-fpipe-endpoint";
            uses svc-common:endpoint-extension;
        } //container
    } //augment fpipe endpoint

}
