module svc-extension-eline {
    yang-version 1.1;
    namespace "urn:nokia:nsp:model:nsp-service:services:service-layer:svc-extension:eline";
    prefix "svc-extension-eline";
    import nsp-model-extensions { prefix model-ext; }
    import service-extension-common { prefix "svc-common"; }
    organization "Nokia";
    contact
        "Nokia NSP Support
         Web: <http://www.nokia.com>";
    description "Adds eline service Augmentation";
    revision "2023-06-27" { description "Move to extension common"; }
    revision "2023-01-30" { description "Eline auto-bind under mpls"; }
    revision "2023-01-20" { description "Eline auto-bind"; }
    revision "2022-10-26" { description "Endpoint tenant-id"; }
    revision "2022-04-19" { description "Add composite service association"; }
    revision "2021-11-30" { description "Add site-id to extension endpoint"; }
    revision "2020-10-13" { description "extension of the eline service-dmodel"; }

    typedef epipe-site-type {
        type enumeration {
            enum standard       { value 0; }
            enum pbb            { value 1; }
            enum evpn           { value 2; }
        }
        description "Specifies the epipe site type.";
    }

    typedef bgp-evpn-force-vc-forwarding {
        type enumeration {
            enum "vlan"   { value 1; }
        }
        description "Force VC forwarding options for BGP EVPN.";
    }

    grouping eline-svc {
        container eline-svc {
            model-ext:table-name "service-extension-eline-svc";
            uses svc-common:svc-extension-common;
        }
    }


    grouping eline-site {
        container eline-site {
            model-ext:table-name "service-extension-eline-site";
            uses svc-common:site-extension;
            leaf site-type {
                type epipe-site-type;
                default standard;
                description "Specifies the site-type for eline services.";
            }
            container pbb {

                leaf force-qtag-forwarding {
                    type boolean;
                    description "Add an IEEE 802.1q tag after the Customer MAC address when the PBB header is built.";
                }

                leaf backbone-vpls-service-name {
                    type string;
                    description "Backbone VPLS service.";
                }
                leaf isid {
                    type int32;
                    description "Service instance ID.";
                }
                leaf backbone-dest-mac {
                    type string;
                    description "Backbone Destination MAC address.";
                }
                leaf backbone-dest-mac-name {
                    type string;
                    description "Name for backbone Destination MAC address.";
                }
            } //container pbb

            uses bgp-evpn;

            list bgp {
                key bgp-instance;
                uses bgp;
            }
        }
    }

    grouping bgp-evpn {
        container bgp-evpn {
            description "An EVPN instance";
            leaf evi {
                type uint32;
                description "The evi.";
            }
            leaf local-ac-name {
                type string;
                description "the local attachement circuit name";
            }
            leaf local-eth-tag {
                type int32;
                description "ethernet tag of the local attachement circuit";
            }
            leaf remote-ac-name {
                type string;
                description "the remote attachement circuit name";
            }
            leaf remote-eth-tag {
                type int32;
                description "ethernet tag of the remote attachement circuit";
            }
            list mpls {
                key "bgp-instance";
                leaf bgp-instance {
                    type int32 {
                        range "1..2";
                    }
                    description "BGP instance";
                }
                leaf force-vc-forwarding {
                    type bgp-evpn-force-vc-forwarding;
                    description "VC forwarding action";
                }
                leaf ecmp {
                    type int32;
                    default "1";
                    description "Maximum ECMP routes information.";
                }
                uses svc-common:l2-auto-bind-tunnel;
            }
        }
    }

    grouping bgp {
        description "BGP parameters common to all pseudowires.";
        leaf bgp-instance {
            type int32 {
                range "1..2";
            }
            description "BGP instance";
        }

        leaf route-distinguisher {
            type union {
                type enumeration {
                    enum "auto-rd" {value 1;}
                }
                type string;
            }
            description "High-order 6 bytes that are used as string to compose VSI-ID for use in NLRI";
        }

        container route-target-import {
            uses svc-common:route-target;
        }

        container route-target-export {
            uses svc-common:route-target;
        }
    }

    grouping eline-endpoint {
        container eline-endpoint {
            model-ext:table-name "service-extension-eline-endpoint";
            uses svc-common:endpoint-extension;
        } //container
    } //augment eline endpoint

}
