module nsp-intent-audit {
    yang-version "1.1";
    namespace "urn:nokia:nsp:nsp-intent-audit";
    prefix "nsp-intent-audit";
    import nsp-model-extensions { prefix model-ext; }
    organization "Nokia";
    description "YANG definition for intent auto audit";
    revision "2023-08-18" { description  "NSP intent auto audit definitions"; }

    grouping nsp-intent-audit-source-def {
        leaf intent-instance {
            type string;
            description "intent instance identify";
        }
        leaf intent-type {
            type string;
            description "intent type";
        }
        leaf source-fdn {
            type string;
            description "source root fdn used to associate the changed plugin objects";
        }
    }

    container intent-sources {
        list intent-source{
            model-ext:table-name "nsp-intent-audit-source";
            key "intent-instance intent-type source-fdn";
            model-ext:index-fields "source-fdn, intent-type";
            uses nsp-intent-audit-source-def;
            model-ext:notif-suppress true;
        }
    }
}
