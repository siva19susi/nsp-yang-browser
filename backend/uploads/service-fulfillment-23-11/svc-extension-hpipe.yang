module svc-extension-hpipe {
    yang-version 1.1;
    namespace "urn:nokia:nsp:model:nsp-service:services:service-layer:svc-extension:hpipe";
    prefix "svc-extension-hpipe";
    import nsp-model-extensions { prefix model-ext; }
    import service-extension-common { prefix "svc-common"; }
    organization "Nokia";
    contact
        "Nokia NSP Support
         Web: <http://www.nokia.com>";
    description "Adds hpipe service Augmentation";
    revision "2023-06-27" { description "Move to extension common"; }
    revision "2022-10-26" { description "Endpoint tenant-id"; }
    revision "2022-10-13" { description "Initial setup"; }

    grouping hpipe-svc {
        container hpipe-svc {
            model-ext:table-name "service-extension-hpipe-svc";
            uses svc-common:svc-extension-common;
        }
    }

    grouping hpipe-site {
        container hpipe-site {
            model-ext:table-name "service-extension-hpipe-site";
            uses svc-common:site-extension;
        }
    }

    grouping hpipe-endpoint {
        container hpipe-endpoint {
            model-ext:table-name "service-extension-hpipe-endpoint";
            uses svc-common:endpoint-extension;
        } //container
    } //augment hpipe endpoint

}
