module svc-extension-gre-tunnel {
    yang-version 1.1;
    namespace "urn:nokia:nsp:model:nsp-service:services:service-layer:svc-extension:gre-tunnel";
    prefix "svc-extension-gre-tunnel";
    import nsp-model-extensions { prefix model-ext; }
    import service-extension-common { prefix "svc-common"; }

    organization "Nokia";
    contact
        "Nokia NSP Support
         Web: <http://www.nokia.com>";
    description "Adds tunnel Augmentation";
    revision "2023-06-27" { description "Move to extension common"; }
    revision "2021-11-06" { description "extension of the tunnel"; }

    grouping gre-tunnel-ext {
        container gre-tunnel-ext {
            model-ext:table-name "service-extension-gre-tunnel-ext";

            uses svc-common:tunnel-extension-common;
        }
    }
}
