module nsp-network {
    yang-version 1.1;
    namespace "urn:nokia:nsp:model:nsp-network";
    prefix nsp-nw;

    import ietf-yang-schema-mount { prefix yangmnt; }

    organization "Nokia";

    contact
        "Nokia NSP Support
         Web: <http://www.nokia.com>";

    description
        "Base data model for a collection of nodes in a network managed by NSP.";


    revision 2020-12-15 {
        description "Initial revision";
    }

    container network {
      list node {
        key "node-id";
        description
          "The inventory of nodes of NSP managed network.";

        leaf node-id {
          type string;
          description
            "Uniquely identifies a node within the NSP Network.";
        }

        yangmnt:mount-point node-root {

        }   // this is the mount point label, which needs to be described in ietf-yang-schema-mount
     }
   }
}
