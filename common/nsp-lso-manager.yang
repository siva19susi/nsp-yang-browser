module nsp-lso-manager {
  yang-version 1.1;
  namespace "urn:nokia:nsp:model:lso:manager";
  prefix nlm;

  import nsp-model-extensions {
    prefix model-ext;
  }
  import ietf-yang-types {
    prefix yang;
  }

  organization
    "Nokia ION NSM NSP";
  contact
    "www.nokia.com";
  description
    "LSO Manager - Operation Type Model.";
    revision 2022-08-22 {
      description
      "NSP 22.9 release changes";
         /*
         "Added new leaf 'signed, signedby' in operation-type"
         */
       reference
       "revision for the release 22.9.0-rel changes.";
    }
    revision 2022-08-02 {
      description
      "NSP 22.9 release changes";
        /*
         "Added new leaf 'version' in operation-type"
         */
      reference
      "revision for the release 22.9.0-rel changes.";
    }
    revision 2022-06-09 {
      description
      "Initial revision.";
        /*
         "Added new leaf 'is-auto-run' in schedule, config false for status"
         */
      reference
      "revision for the release 22.6.0-rel changes.";
    }
  revision 2022-06-09 {
    description
      "NSP 22.6 release changes.";
    /*
     Changes in this revision:
     	Changed range  "1..255" for concurrency count to fix PTS  NSPD-293664  
     */
    reference
      "";
  }
    revision 2021-10-26 {
    description
      "NSP 21.11 release changes.";
    /*
     Changes in this revision:
     Added the following changes to support NSPF-228425 :
      - Added new leaf 'input-parameters' in schedule
     */
    reference
      "";
  }

revision 2022-05-17 {
   description
     "Initial revision.";
  /*
   "Changes in this revision:
      Added the following changes to support rolback feature :
        Added type 'mode' which defines mode of action on execution {}
  */
   reference
     "Revision for the release 22.6.0-rel changes.";
 }
  revision 2021-06-28 {
    description
      "NSP 21.11 release changes.";
    /*
     Changes in this revision:
     Added the following changes to support phasing feature :
      - Defined 'phase-definition' list in 'operation-type'
      - Added new leaf 'phase-name' in schedule
     Following changes as part of execution control feature :
      - Defined grouping 'execution-control-parameters'
      - Use group 'execution-control-parameters' in 'schedule'    
     */
    reference
      "";
  }
  revision 2020-06-25 {
    description
      "Initial revision.";
    reference
      "";
  }

  typedef operation-category {
    type enumeration {
      enum backup {
        value 0;
        description
          "Backup";
      }
      enum restore {
        value 1;
        description
          "Restore";
      }
      enum upgrade {
        value 2;
        description
          "Upgrade";
      }
      enum other {
        value 3;
        description
          "Other";
      }
    }
    description
      "Specifies the category of the operation.";
  }

  typedef schedule-status {
    type enumeration {
      enum scheduled {
        value 0;
        description
          "Scheduled.";
      }
      enum cancelled {
        value 1;
        description
          "Schedule cancelled.";
      }
      enum not-scheduled {
        value 2;
        description
          "Not scheduled.";
      }
      enum completed {
        value 3;
        description
          "Schedule completed.";
      }
    }
    description
      "Specifies the status of the Schedule.";
  }

  typedef life-cycle-state {
    type enumeration {
      enum draft {
        value 0;
        description
          "The initial state of the created operation-type. In this state operation-type is allowed to edit.";
      }
      enum released {
        value 1;
        description
          "Only released operation-types can be used for operation/schedule creation. Editing of released operation-type is not allowed.";
      }
      enum withdrawn {
        value 2;
        description
          "The withdrawn operation-types can not be used for operation/schedule creation.";
      }
    }
    description
      "Specifies the life cycle of the operation type.";
  }
  
  typedef mode {
    type enumeration {
      enum normal {
        value 0;
        description
          "Indicates the noraml execution flow.";
      }
      enum re-run {
        value 1;
        description
          "Indicates the execution is triggered via re-run.";
      }
      enum roll-back {
        value 2;
        description
          "Indicates the execution is triggered via roll-back.";
      }
    }
    description
      "Specifies the mode of action on execution.";
  }

  grouping execution-control-parameters-global {
    description
      "Group of operation level execution control parameters.";
    leaf failure-threshold {
      type uint8 {
        range "1..100";
      }
      description
        "It is a percenatage of failure executions. Operation will be stopped once this threshold is reached.";
    }
    leaf window-size {
      type uint16 {
        range "1..2000";
      }
      description
        "Window size to consider for calculating failure threshold.";
    }
  }

  grouping execution-control-parameters {
    description
      "Group of phase level execution control parameters.";
    leaf concurrency-count {
      type uint8 {
         range "1..255";
      }
      default 20;
      description
        "Count of concurrent executions allowed.";
    }
    leaf average-execution-time-threshold {
      type uint16;
      description
        "Average execution time.";
    }
    leaf phase-timeout {
      type uint16;
      description
        "The phase timeout.";
    }
  }

  container lso-manager {
    description
      "Large scale operation manager objects.";
    container operation-types {
      description
        "Operation types defined in the system.";
      list operation-type {
        model-ext:custom-impl "java" {
          model-ext:class "com.nokia.nsp.lsom.operationtype.transaction.OperationTypeTransactionHandler";
        }
        model-ext:table-name "operationtype";
        key "name";
        ordered-by system;
        description
          "List of the operation-types.";
        leaf name {
          type string {
            length "1..30";
            pattern '[0-9a-zA-Z-]*';
          }
          description
            "Name of the operation-type (for example: ne-backup).";
        }
        leaf description {
          type string;
          description
            "Description of the operation-type.";
        }
        leaf category {
          type operation-category;
          description
            "Category of the operation-type.";
        }
        leaf-list additional-tag {
          type string {
            length "0..30";
            pattern '[0-9a-zA-Z_-]*';
          }
          description
            "Additional tags of the operation-type.";
        }
        leaf life-cycle-state {
          type life-cycle-state;
          default "draft";
          description
            "Indicates the life-cycle-state of the operation.";
        }
        leaf created-by {
          type string;
          config false;
          description
            "Author of the operation-type.";
        }
        leaf predefined {
          type boolean;
          default "false";
          config false;
          description
            "Indicates if this is a predefined Operation Type, i.e Operation type delivered by Nokia.";
        }
        leaf operation-model {
          type string;
          description
            "Extension model of the operation type.";
        }
        leaf profile {
          type string {
            length "0..10485760";
          }
          description
            "Profile definition in yaml format.";
        }
        leaf creation-status {
          type string;
          config false;
          description
            "Operation-type creation status.";
        }
        leaf creation-time {
          type yang:date-and-time;
          config false;
          description
            "The operation-type's creation time.";
        }
        leaf last-modified-time {
          type yang:date-and-time;
          config false;
          description
            "The last updated time of the operation-type.";
        }
        leaf internal {
          type boolean;
          default "false";
          config false;
          description
            "Indicates if this is a internal operation-type.";
        }
        leaf version {
          type string{
            pattern '^(\d+\.)?(\d+\.)?(\*|\d+)$';
          }
          default "0.0.0";
          description
            "Indicates the version of the operation-type";
        }
        leaf signed {
          type boolean;
          default "false";
          config false;
          description
            "Indicates whether the operation-type is signed or not";
        }
        leaf signed-by {
          type string;
          config false;
          description
            "Indicates the author name for the signed operation-type";
        }

        uses execution-control-parameters-global;
        list phase-definition {
          model-ext:table-name "phase-definition";
          key "name";
          config false;
          ordered-by user;
          description
            "Phase definitions of an Operation-Type.";
          leaf name {
            type string;
            description
              "Name of the phase.";
          }
          leaf description {
            type string;
            description
              "Phase description.";
          }
          leaf sequence-id {
            type uint8;
            description
              "Order at which the phase runs.";
          }
          leaf rollback-allowed {
          type boolean;
          default "false";
          config false;
          description
            "Indicates whether the phase executions can be rollback or not";
        }
          uses execution-control-parameters;
        }
      }
    }
    container default-operation-types {
      description
        "Inidcates the Default Operation Type for a given category.";
      list default-operation-type-per-category {
        model-ext:custom-impl "java" {
          model-ext:class "com.nokia.nsp.lsom.operationtype.transaction.DefaultOperationTypesPerCategoryTransactionHandler";
        }
        model-ext:table-name "default-operation-type-per-category";
        key "category";
        ordered-by system;
        description
          "List of category wise default operation-types.";
        leaf category {
          type operation-category;
          description
            "Category of the operation-type.";
        }
        leaf default-operation-type {
          type leafref {
            path "/lso-manager/operation-types/operation-type/name";
          }
          description
            "Name of the default operation-type.";
        }
      }
    }
    container schedules {
      description
        "Schedule operation metadata.";
      list schedule {
        model-ext:table-name "schedule";
        model-ext:custom-impl "java" {
          model-ext:class "com.nokia.nsp.lsom.schedule.transaction.ScheduleTransactionHandler";
        }
        key "operation-type name";
        ordered-by system;
        description
          "List of schedules metadata.";
        leaf name {
          type string {
            //length "1..30";
            pattern '[0-9a-zA-Z_-]*';
          }
          description
            "Name of the schedule.";
        }
        leaf operation-type {
          type leafref {
            path "/lso-manager/operation-types/operation-type/name";
          }
          description
            "The operation-type which is scheduled";
        }
        leaf-list target {
          type string;
          description
            "List of targets. Target can be NetworkElementGroup or NetworkElement.";
        }
        leaf pattern {
          type string;
          description
            "It is a cron expression.";
        }
        leaf repeats {
          type string;
          description
            "Indicates frequency of schedule.";
        }
        leaf status {
          type schedule-status;
          config false;
          description
            "Schedule status.";
        }
        leaf scheduled-operation {
          type string;
          config false;
          description
            "Next operation scheduled to run.";
        }
        leaf additional-info {
          type string;
          config false;
          description
            "Additional information.";
        }
        leaf created-by {
          type string;
          config false;
          description
            "Author of the Schedule.";
        }
        leaf creation-time {
          type yang:date-and-time;
          config false;
          description
            "Indicates the date and time when the schedule was created.";
        }
        leaf last-modified-time {
          type yang:date-and-time;
          config false;
          description
            "Indicates the date and time when the schedule was last updated.";
        }
        leaf start-time {
          type yang:date-and-time;
          config false;
          description
            "Indicates the date and time when the schedule will start.";
        }
        leaf end-time {
          type yang:date-and-time;
          description
            "Indicates the date and time when the schedule will end. If it is not set, schedule will run forever.";
        }
        leaf skipping-enabled {
          type boolean;
          default "false";
          description
            "When skipping-enabled is true, new Operation will be skipped if the Previous one is still in progress. skipping-enabled is false new operation will run even if the previous oprtaion is in Progress";
        }
        leaf is-enabled {
          type boolean;
          default "true";
          config false;
          description
            "Indicates if the schedule is enabled. Schedule can be enabled only for released operation-types.";
        }
        leaf previous-operation {
          type string;
          config false;
          description
            "Operation that ran in previous schedule interval.";
        }
        leaf time-zone {
          type string;
          description
            "Indicates the time zone that schedule should run on.";
        }
        leaf description {
          type string;
          description
            "Description of the Schedule.";
        }
        leaf phase-name {
          type string;
          default "";
          config false;
          description
            "Name of the phase this schedule belongs to. This field will not be populated for single phased operation schedules.";
        }
        leaf is-auto-run {
          type boolean;
          default "false";
          description
            "True Indicates that it should run the operation directly";
        }
        leaf input-parameters {
          type string {
          length "0..10485760";
          }
          description
            "Input Parameters for the Operation in JSON Format";
        }
        uses execution-control-parameters-global;
        uses execution-control-parameters;
      }
    }
  }
  rpc operation-type-creation-from-cam-rpc {
    description
      "RPC is used too add the signature information into operation type";
    model-ext:operation "java" {
      model-ext:class "com.nokia.nsp.lsom.operationtype.rpc.OperationTypeCreationFromCamRpcImpl";
    }
    input {
      list operation-type {
        leaf name {
          type string;
          description
            "Operation type";
        }
        leaf description {
          type string;
          description
            "description";
        }
        leaf category {
          type string;
          description
            "category";
        }
        leaf profile {
          type string;
          description
            "profile";
        }
        leaf-list additional-tag {
          type string;
          description
            "additional-tag";
        }
        leaf operation-model {
          type string;
          description
            "operation-model";
        }
        leaf life-cycle-state {
          type string;
          description
            "Indicates the life-cycle-state of the operation.";
        }
        leaf version {
          type string;
          description
          "Indicates the version of the operation-type";
        }
        leaf signed {
          type boolean;
          description
            "Indicates whether the operation-type is signed or not";
        }
        leaf signed-by {
          type string;
          description
             "Indicates the author name for the signed operation-type";
         }
        leaf failure-threshold {
          type uint8;
          description
          "It is a percenatage of failure executions. Operation will be stopped once this threshold is reached.";
        }
        leaf window-size {
          type uint16;
          description
          "Window size to consider for calculating failure threshold.";
        }
        }
        leaf pem-key {
          type string;
          description
            "pem key";
        }
        leaf is-create {
          type string;
          description
            "Is create or update";
        }
    }
    output {
      anydata data {
        description
          "Copy of the data subset that matched
           the filter (if any). An empty data container
           indicates that the request did not produce any results.";
      }
    }
  }
}
